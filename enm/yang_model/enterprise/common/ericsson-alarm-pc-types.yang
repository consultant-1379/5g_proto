module ericsson-alarm-pc-types {
	yang-version 1.1;
  	namespace urn:rdns:com:ericsson:oammodel:ericsson-alarm-pc-types;
  	prefix fmpce;

	import ericsson-yang-extensions { prefix yexte; }
	
	organization "Ericsson AB";
	contact "Ericsson first line support via email";
	description "Contains types used by Fault Management
		
		Copyright (c) 2018 Ericsson AB. All rights reserved.";
		
	yexte:library-module;

  	revision 2018-11-21 {
    	description "Added the following value from RFC 3877:
					    other (1024).
			Added the set of 'Enterprise added values', 10.1.1026,
			from ERICSSON-ROUTER-ALARM-TC MIB.
			Fixed typo in description of eri-probable-cause enum";
		yexte:version "2";
		yexte:release "1";
		yexte:correction "0";
  	}
  	
  	revision 2017-05-15 {
    	description "Updated prefix";
		yexte:version "2";
		yexte:release "0";
		yexte:correction "0";
  	}

  	revision 2016-12-02 {
    	description "Generated by confdc --mib2yang
			Source: ERICSSON-ALARM-PC-MIB.mib
			Changed to look like yang.";
		yexte:version "1";
		yexte:release "0";
		yexte:correction "1";
  	}


  typedef eri-probable-cause {
    type enumeration {
      enum "m3100-indeterminate" {
        value 0;
      }
      enum "m3100-alarm-indication-signal" {
        value 1;
      }
      enum "m3100-call-setup-failure" {
        value 2;
      }
      enum "m3100-degraded-signal" {
        value 3;
      }
      enum "m3100-far-end-receiver-failure" {
        value 4;
      }
      enum "m3100-framing-error" {
        value 5;
      }
      enum "m3100-loss-of-frame" {
        value 6;
      }
      enum "m3100-loss-of-pointer" {
        value 7;
      }
      enum "m3100-loss-of-signal" {
        value 8;
      }
      enum "m3100-payload-type-mismatch" {
        value 9;
      }
      enum "m3100-transmission-error" {
        value 10;
      }
      enum "m3100-remote-alarm-interface" {
        value 11;
      }
      enum "m3100-excessive-bit-error-rate" {
        value 12;
      }
      enum "m3100-path-trace-mismatch" {
        value 13;
      }
      enum "m3100-unavailable" {
        value 14;
      }
      enum "m3100-signal-label-mismatch" {
        value 15;
      }
      enum "m3100-loss-of-multi-frame" {
        value 16;
      }
      enum "receive-failure" {
        value 17;
      }
      enum "transmit-failure" {
        value 18;
      }
      enum "modulation-failure" {
        value 19;
      }
      enum "demodulation-failure" {
        value 20;
      }
      enum "broadcast-channel-failure" {
        value 21;
      }
      enum "connection-establishment-error" {
        value 22;
      }
      enum "invalid-message-received" {
        value 23;
      }
      enum "local-node-transmission-error" {
        value 24;
      }
      enum "remote-node-transmission-error" {
        value 25;
      }
      enum "routing-failure" {
        value 26;
      }
      enum "m3100-back-plane-failure" {
        value 51;
      }
      enum "m3100-data-set-problem" {
        value 52;
      }
      enum "m3100-equipment-identifier-duplication" {
        value 53;
      }
      enum "m3100-external-if-device-problem" {
        value 54;
      }
      enum "m3100-line-card-problem" {
        value 55;
      }
      enum "m3100-multiplexer-problem" {
        value 56;
      }
      enum "m3100-ne-identifier-duplication" {
        value 57;
      }
      enum "m3100-power-problem" {
        value 58;
      }
      enum "m3100-processor-problem" {
        value 59;
      }
      enum "m3100-protection-path-failure" {
        value 60;
      }
      enum "m3100-receiver-failure" {
        value 61;
      }
      enum "m3100-replaceable-unit-missing" {
        value 62;
      }
      enum "m3100-replaceable-unit-type-mismatch" {
        value 63;
      }
      enum "m3100-synchronisation-source-mismatch" {
        value 64;
      }
      enum "m3100-terminal-problem" {
        value 65;
      }
      enum "m3100-timing-problem" {
        value 66;
      }
      enum "m3100-transmitter-failure" {
        value 67;
      }
      enum "m3100-trunk-card-problem" {
        value 68;
      }
      enum "m3100-replaceable-unit-problem" {
        value 69;
      }
      enum "real-time-clock-failure" {
        value 70;
      }
      enum "antenna-failure" {
        value 71;
      }
      enum "battery-charging-failure" {
        value 72;
      }
      enum "disk-failure" {
        value 73;
      }
      enum "frequency-hopping-failure" {
        value 74;
      }
      enum "io-device-error" {
        value 75;
      }
      enum "loss-of-synchronisation" {
        value 76;
      }
      enum "loss-of-redundancy" {
        value 77;
      }
      enum "power-supply-failure" {
        value 78;
      }
      enum "signal-quality-evaluation-failure" {
        value 79;
      }
      enum "tranceiver-failure" {
        value 80;
      }
      enum "protection-mechanism-failure" {
        value 81;
      }
      enum "protecting-resource-failure" {
        value 82;
      }
      enum "m3100-air-compressor-failure" {
        value 101;
      }
      enum "m3100-air-conditioning-failure" {
        value 102;
      }
      enum "m3100-air-dryer-failure" {
        value 103;
      }
      enum "m3100-battery-discharging" {
        value 104;
      }
      enum "m3100-battery-failure" {
        value 105;
      }
      enum "m3100-commercial-power-failure" {
        value 106;
      }
      enum "m3100-cooling-fan-failure" {
        value 107;
      }
      enum "m3100-engine-failure" {
        value 108;
      }
      enum "m3100-fire-detector-failure" {
        value 109;
      }
      enum "m3100-fuse-failure" {
        value 110;
      }
      enum "m3100-generator-failure" {
        value 111;
      }
      enum "m3100-low-battery-threshold" {
        value 112;
      }
      enum "m3100-pump-failure" {
        value 113;
      }
      enum "m3100-rectifier-failure" {
        value 114;
      }
      enum "m3100-rectifier-high-voltage" {
        value 115;
      }
      enum "m3100-rectifier-low-voltage" {
        value 116;
      }
      enum "m3100-ventilation-system-failure" {
        value 117;
      }
      enum "m3100-enclosure-door-open" {
        value 118;
      }
      enum "m3100-explosive-gas" {
        value 119;
      }
      enum "m3100-fire" {
        value 120;
      }
      enum "m3100-flood" {
        value 121;
      }
      enum "m3100-high-humidity" {
        value 122;
      }
      enum "m3100-high-temperature" {
        value 123;
      }
      enum "m3100-high-wind" {
        value 124;
      }
      enum "m3100-ice-build-up" {
        value 125;
      }
      enum "m3100-low-fuel" {
        value 127;
      }
      enum "m3100-low-humidity" {
        value 128;
      }
      enum "m3100-low-cable-pressure" {
        value 129;
      }
      enum "m3100-low-temperature" {
        value 130;
      }
      enum "m3100-low-water" {
        value 131;
      }
      enum "m3100-smoke" {
        value 132;
      }
      enum "m3100-toxic-gas" {
        value 133;
      }
      enum "m3100-cooling-system-failure" {
        value 134;
      }
      enum "m3100-external-equipment-failure" {
        value 135;
      }
      enum "m3100-external-point-failure" {
        value 136;
      }
      enum "m3100-storage-capacity-problem" {
        value 151;
      }
      enum "m3100-memory-mismatch" {
        value 152;
      }
      enum "m3100-corrupt-data" {
        value 153;
      }
      enum "m3100-out-of-cpu-cycles" {
        value 154;
      }
      enum "m3100-software-environment-problem" {
        value 155;
      }
      enum "m3100-software-download-failure" {
        value 156;
      }
      enum "m3100-loss-of-real-timel" {
        value 157;
      }
      enum "application-subsystem-failure" {
        value 158;
      }
      enum "configuration-or-customisation-error" {
        value 159;
      }
      enum "database-inconsistency" {
        value 160;
      }
      enum "file-error" {
        value 161;
      }
      enum "out-of-memory" {
        value 162;
      }
      enum "software-error" {
        value 163;
      }
      enum "timeout-expired" {
        value 164;
      }
      enum "underlaying-resource-unavailable" {
        value 165;
      }
      enum "version-mismatch" {
        value 166;
      }
      enum "bandwidth-reduced" {
        value 201;
      }
      enum "congestion" {
        value 202;
      }
      enum "excessive-error-rate" {
        value 203;
      }
      enum "excessive-response-time" {
        value 204;
      }
      enum "excessive-retransmission-rate" {
        value 205;
      }
      enum "reduced-logging-capability" {
        value 206;
      }
      enum "system-resources-overload" {
        value 207;
      }
      enum "x733-adapter-error" {
        value 301;
      }
      enum "x733-application-subsystem-failure" {
        value 302;
      }
      enum "x733-bandwidth-reduced" {
        value 303;
      }
      enum "x733-communications-protocol-error" {
        value 305;
      }
      enum "x733-communications-subsystem-failure" {
        value 306;
      }
      enum "x733-configuration-or-customization-error" {
        value 307;
      }
      enum "x733-congestion" {
        value 308;
      }
      enum "x733-cpu-cycles-limit-exceeded" {
        value 310;
      }
      enum "x733-data-set-or-modem-error" {
        value 311;
      }
      enum "x733-dte-dce-interface-error" {
        value 313;
      }
      enum "x733-equipment-malfunction" {
        value 315;
      }
      enum "x733-excessive-vibration" {
        value 316;
      }
      enum "x733-file-error" {
        value 317;
      }
      enum "x733-heating-or-ventilation-or-cooling-system-problem" {
        value 321;
      }
      enum "x733-humidity-unacceptable" {
        value 322;
      }
      enum "x733-input-output-device-error" {
        value 323;
      }
      enum "x733-input-device-error" {
        value 324;
      }
      enum "x733-lane-error" {
// Spelling mistake left in place to maintain compatibility with 
// earlier versions of ericsson-alarm-pc-types.yang and 
// ERICSSON-ALARM-PC-MIB.
        value 325;
      }
      enum "x733-leak-detected" {
        value 326;
      }
      enum "x733-local-node-transmission-error" {
        value 327;
      }
      enum "x733-material-supply-exhausted" {
        value 330;
      }
      enum "x733-out-of-memory" {
        value 332;
      }
      enum "x733-ouput-device-error" {
// Spelling mistake left in place to maintain compatibility with 
// earlier versions of ericsson-alarm-pc-types.yang and 
// ERICSSON-ALARM-PC-MIB.
        value 333;
      }
      enum "x733-performance-degraded" {
        value 334;
      }
      enum "x733-pressure-unacceptable" {
        value 336;
      }
      enum "x733-queue-size-exceeded" {
        value 339;
      }
      enum "x733-receive-failure" {
        value 340;
      }
      enum "x733-remote-node-transmission-error" {
        value 342;
      }
      enum "x733-resource-at-or-nearing-capacity" {
        value 343;
      }
      enum "x733-response-time-excessive" {
        value 344;
      }
      enum "x733-retransmission-rate-excessive" {
        value 345;
      }
      enum "x733-software-error" {
        value 346;
      }
      enum "x733-software-program-abnormally-terminated" {
        value 347;
      }
      enum "x733-software-program-error" {
        value 348;
      }
      enum "x733-temperature-unacceptable" {
        value 350;
      }
      enum "x733-threshold-crossed" {
        value 351;
      }
      enum "x733-toxic-leak-detected" {
        value 353;
      }
      enum "x733-transmit-failure" {
        value 354;
      }
      enum "x733-underlying-resource-unavailable" {
        value 356;
      }
      enum "x733-version-mismatch" {
        value 357;
      }
      enum "x736-authentication-failure" {
        value 401;
      }
      enum "x736-breach-of-confidentiality" {
        value 402;
      }
      enum "x736-cable-tamper" {
        value 403;
      }
      enum "x736-delayed-information" {
        value 404;
      }
      enum "x736-denial-of-service" {
        value 405;
      }
      enum "x736-duplicate-information" {
        value 406;
      }
      enum "x736-information-missing" {
        value 407;
      }
      enum "x736-information-modification-detected" {
        value 408;
      }
      enum "x736-information-out-of-sequence" {
        value 409;
      }
      enum "x736-intrusion-detection" {
        value 410;
      }
      enum "x736-key-expired" {
        value 411;
      }
      enum "x736-non-repudiation-failure" {
        value 412;
      }
      enum "x736-out-of-hours-activity" {
        value 413;
      }
      enum "x736-out-of-service" {
        value 414;
      }
      enum "x736-procedural-error" {
        value 415;
      }
      enum "x736-unauthorized-access-attempt" {
        value 416;
      }
      enum "x736-unexpected-information" {
        value 417;
      }
      enum "x736-unspecified-reason" {
        value 418;
      }
      enum "gsm1211-abis-to-bts-interface-failure" {
        value 501;
      }
      enum "gsm1211-abis-to-trx-interface-failure" {
        value 502;
      }
      enum "gsm1211-antenna-problem" {
        value 503;
      }
      enum "gsm1211-battery-breakdown" {
        value 504;
      }
      enum "gsm1211-battery-charging-fault" {
        value 505;
      }
      enum "gsm1211-clock-synchronisation-problem" {
        value 506;
      }
      enum "gsm1211-combiner-problem" {
        value 507;
      }
      enum "gsm1211-disk-problem" {
        value 508;
      }
      enum "gsm1211-excessive-receiver-temperature" {
        value 510;
      }
      enum "gsm1211-excessive-transmitter-output-power" {
        value 511;
      }
      enum "gsm1211-excessive-transmitter-temperature" {
        value 512;
      }
      enum "gsm1211-frequency-hopping-degraded" {
        value 513;
      }
      enum "gsm1211-frequency-hopping-failure" {
        value 514;
      }
      enum "gsm1211-frequency-redefinition-failed" {
        value 515;
      }
      enum "gsm1211-line-interface-failure" {
        value 516;
      }
      enum "gsm1211-link-failure" {
        value 517;
      }
      enum "gsm1211-loss-of-synchronisation" {
        value 518;
      }
      enum "gsm1211-lost-redundancy" {
        value 519;
      }
      enum "gsm1211-mains-breakdown-with-battery-back-up" {
        value 520;
      }
      enum "gsm1211-mains-breakdown-without-battery-back-up" {
        value 521;
      }
      enum "gsm1211-power-supply-failure" {
        value 522;
      }
      enum "gsm1211-receiver-antenna-fault" {
        value 523;
      }
      enum "gsm1211-receiver-multicoupler-failure" {
        value 525;
      }
      enum "gsm1211-reduced-transmitter-output-power" {
        value 526;
      }
      enum "gsm1211-signal-quality-evaluation-fault" {
        value 527;
      }
      enum "gsm1211-timeslot-hardware-failure" {
        value 528;
      }
      enum "gsm1211-transceiver-problem" {
        value 529;
      }
      enum "gsm1211-transcoder-problem" {
        value 530;
      }
      enum "gsm1211-transcoder-or-rate-adapter-problem" {
        value 531;
      }
      enum "gsm1211-transmitter-antenna-failure" {
        value 532;
      }
      enum "gsm1211-transmitter-antenna-not-adjusted" {
        value 533;
      }
      enum "gsm1211-transmitter-low-voltage-or-current" {
        value 535;
      }
      enum "gsm1211-transmitter-off-frequency" {
        value 536;
      }
      enum "gsm1211-database-inconsistency" {
        value 537;
      }
      enum "gsm1211-file-system-call-unsuccessful" {
        value 538;
      }
      enum "gsm1211-input-parameter-out-of-range" {
        value 539;
      }
      enum "gsm1211-invalid-parameter" {
        value 540;
      }
      enum "gsm1211-invalid-pointer" {
        value 541;
      }
      enum "gsm1211-message-not-expected" {
        value 542;
      }
      enum "gsm1211-message-not-initialised" {
        value 543;
      }
      enum "gsm1211-message-out-of-sequence" {
        value 544;
      }
      enum "gsm1211-system-call-unsuccessful" {
        value 545;
      }
      enum "gsm1211-timeout-expired" {
        value 546;
      }
      enum "gsm1211-variable-out-of-range" {
        value 547;
      }
      enum "gsm1211-watch-dog-timer-expired" {
        value 548;
      }
      enum "gsm1211-cooling-system-failure" {
        value 549;
      }
      enum "gsm1211-external-equipment-failure" {
        value 550;
      }
      enum "gsm1211-external-power-supply-failure" {
        value 551;
      }
      enum "gsm1211-external-transmission-device-failure" {
        value 552;
      }
      enum "gsm1211-reduced-alarm-reporting" {
        value 561;
      }
      enum "gsm1211-reduced-event-reporting" {
        value 562;
      }
      enum "gsm1211-reduced-logging-capability" {
        value 563;
      }
      enum "gsm1211-system-resources-overload" {
        value 564;
      }
      enum "gsm1211-broadcast-channel-failure" {
        value 565;
      }
      enum "gsm1211-connection-establishment-error" {
        value 566;
      }
      enum "gsm1211-invalid-message-received" {
        value 567;
      }
      enum "gsm1211-invalid-msu-received" {
        value 568;
      }
      enum "gsm1211-lapd-link-protocol-failure" {
        value 569;
      }
      enum "gsm1211-local-alarm-indication" {
        value 570;
      }
      enum "gsm1211-remote-alarm-indication" {
        value 571;
      }
      enum "gsm1211-routing-failure" {
        value 572;
      }
      enum "gsm1211-ss7-protocol-failure" {
        value 573;
      }
      enum "gsm1211-transmission-error" {
        value 574;
      }
      enum "i610-loc-end-to-end" {
        value 600;
      }
      enum "i610-ais-end-to-end" {
        value 601;
      }
      enum "i610-rdi-end-to-end" {
        value 602;
      }
      enum "i610-loc-segment-link-side" {
        value 603;
      }
      enum "i610-loc-segment-core-side" {
        value 604;
      }
      enum "i610-ais-segment-link-side" {
        value 605;
      }
      enum "i610-ais-segment-core-side" {
        value 606;
      }
      enum "i610-rdi-segment-link-side" {
        value 607;
      }
      enum "i610-rdi-segment-core-side" {
        value 608;
      }
// Added "Enterprise-specific mappings from ERICSSON-ROUTER-ALARM-TC MIB:     
      enum "loss-of-timing-source" {
        value 1001;
      }         
      enum "aps-channel-processing-failure" {
        value 1002;
      }         
      enum "aps-byte-failure" {
        value 1003;
      }
      enum "aps-channel-match-failure" {
        value 1004;
      }
      enum "aps-mode-mismatch" {
        value 1005;
      }
      enum "loss-of-tu-multiframe-indicator" {
        value 1007;
      }
      enum "path-selector-failure" {
        value 1010;
      }
      enum "blsr-default-kbytes" {
        value 1011;
      }
      enum "blsr-inconsistent-aps-codes" {
        value 1012;
      }
      enum "blsr-node-id-mismatch" {
        value 1013;
      }
      enum "blsr-improper-aps-codes" {
        value 1014;
      }
      enum "blsr-squelching" {
        value 1015;
      }
      enum "blsr-invalid-neighbour" {
        value 1016;
      }
      enum "blsr-invalid-ring-map" {
        value 1017;
      }
      enum "blsr-invalid-ring-id" {
        value 1018;
      }
      enum "blsr-incomplete-ring-config" {
        value 1019;
      }
      enum "blsr-incomplete-et-config" {
        value 1020;
      }
      enum "blsr-node-incorrect-orientation" {
        value 1021;
      }
      enum "hw-resource-exhausted" {
        value 1022;
      }
      enum "hw-resource-threshold" {
        value 1023;
      }
      enum "other" {
        value 1024;
      }
      enum "pw-outage" {
        value 1025;
      }
      enum "er-configuration-or-customization-error" {
// Prefixed with "er-" for "Ericsson Router", to avoid clash with
// the string already assigned to value 100506.
        value 1026;
      }
      
      enum "authentication-failure" {
		value 1600;
      }
      enum "breach-of-confidentiality" {
        value 1601;
      }
      enum "cable-tamper" {
        value 1602;
      }
      enum "delayed-information" {
        value 1603;
      }
      enum "denial-of-service" {
        value 1604;
      }
      enum "duplicate-information" {
        value 1605;
      }
      enum "information-missing" {
        value 1606;
      }
      enum "information-modification-detected" {
        value 1607;
      }
      enum "information-out-of-sequence" {
        value 1608;
      }
      enum "key-expired" {
        value 1609;
      }
      enum "non-repudiation-failure" {
        value 1610;
      }
      enum "out-of-hours-activity" {
        value 1611;
      }
      enum "out-of-service" {
        value 1612;
      }
      enum "procedural-error" {
        value 1613;
      }
      enum "unauthorized-access-attempt" {
        value 1614;
      }
      enum "unexpected-information" {
        value 1615;
      }
      enum "adapter-error" {
        value 100500;
      }
      enum "application-subsystem-failture" {
        value 100501;
      }
      enum "bandwidth-reduced-x733" {
        value 100502;
      }
      enum "call-establishment-error" {
        value 100503;
      }
      enum "communications-protocol-error" {
        value 100504;
      }
      enum "communications-subsystem-failure" {
        value 100505;
      }
      enum "configuration-or-customization-error" {
        value 100506;
      }
      enum "congestion-x733" {
        value 100507;
      }
      enum "corupt-data" {
        value 100508;
      }
      enum "cpu-cycles-limit-exceeded" {
        value 100509;
      }
      enum "data-set-or-modem-error" {
        value 100510;
      }
      enum "degraded-signal-x733" {
        value 100511;
      }
      enum "dte-dce-interface-error" {
        value 100512;
      }
      enum "enclosure-door-open-x733" {
        value 100513;
      }
      enum "equipment-malfunction" {
        value 100514;
      }
      enum "excessive-vibration" {
        value 100515;
      }
      enum "file-error-x733" {
        value 100516;
      }
      enum "fire-detected" {
        value 100517;
      }
      enum "framing-error-x733" {
        value 100518;
      }
      enum "heating-vent-cooling-system-problem" {
        value 100519;
      }
      enum "humidity-unacceptable" {
        value 100520;
      }
      enum "input-output-device-error" {
        value 100521;
      }
      enum "input-device-error" {
        value 100522;
      }
      enum "lan-error" {
        value 100523;
      }
      enum "leak-detected" {
        value 100524;
      }
      enum "local-node-transmission-error-x733" {
        value 100525;
      }
      enum "loss-of-frame-x733" {
        value 100526;
      }
      enum "loss-of-signal-x733" {
        value 100527;
      }
      enum "material-supply-exhausted" {
        value 100528;
      }
      enum "multiplexer-problem-x733" {
        value 100529;
      }
      enum "out-of-memory-x733" {
        value 100530;
      }
      enum "ouput-device-error" {
// Spelling mistake left in place to maintain compatibility with 
// earlier versions of ericsson-alarm-pc-types.yang and 
// ERICSSON-ALARM-PC-MIB.
        value 100531;
      }
      enum "performance-degraded" {
        value 100532;
      }
      enum "power-problems" {
        value 100533;
      }
      enum "pressure-unacceptable" {
        value 100534;
      }
      enum "processor-problems" {
        value 100535;
      }
      enum "pump-failure-x733" {
        value 100536;
      }
      enum "queue-size-exceeded" {
        value 100537;
      }
      enum "receive-failure-x733" {
        value 100538;
      }
      enum "receiver-failure-x733" {
        value 100539;
      }
      enum "remote-node-transmission-error-x733" {
        value 100540;
      }
      enum "resource-at-or-nearing-capacity" {
        value 100541;
      }
      enum "response-time-execessive" {
        value 100542;
      }
      enum "retransmission-rate-excessive" {
        value 100543;
      }
      enum "software-error-x733" {
        value 100544;
      }
      enum "software-program-abnormally-terminated" {
        value 100545;
      }
      enum "software-program-error" {
        value 100546;
      }
      enum "storage-capacity-problem-x733" {
        value 100547;
      }
      enum "temperature-unacceptable" {
        value 100548;
      }
      enum "threshold-crossed" {
        value 100549;
      }
      enum "timing-problem-x733" {
        value 100550;
      }
      enum "toxic-leak-detected" {
        value 100551;
      }
      enum "transmit-failure-x733" {
        value 100552;
      }
      enum "transmiter-failure" {
        value 100553;
      }
      enum "underlying-resource-unavailable" {
        value 100554;
      }
      enum "version-mismatch-x733" {
        value 100555;
      }
    }
    description "Probable cause values from a number of standards.";
  }
}

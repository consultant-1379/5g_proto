module ericsson-diameter-adp {
  yang-version 1.1;
  namespace "urn:rdns:com:ericsson:oammodel:ericsson-diameter-adp";
  prefix diaadp;

  import ericsson-yang-extensions {
    prefix yexte;
  }
  import ietf-inet-types {
    prefix inet;
  }

  //imports for TLS
  import ietf-keystore {
    prefix ks;
    revision-date 2019-11-20; //Draft only
  }
  import ietf-truststore {
    prefix ts;
    revision-date 2019-11-20; //Draft only
  }

  import ericsson-sctp-adp {
    prefix sctpadp;
  }

  import ietf-netconf-acm {
      prefix nacm;
      reference
    "RFC 8341: Network Configuration Access Control Model";
  }
  organization "Ericsson AB";
  contact "Ericsson first line support via email.";
  description "Diameter module for ADP. Diameter provides a standards compliant
  implementation of the Diameter base protocol (RFC 6733) which should be used
  when Authentication, Authorization and Accounting (AAA) Services targeting
  fixed and mobile networks are to be implemented.
  ---
  Copyright Ericsson AB [2022]. All rights reserved";

  revision 2022-12-06 {
    description "SCTP MH support with SENP";
    yexte:version "1";
    yexte:release "13";
    yexte:correction "0";
    reference "RFC 6733: Diameter Base Protocol";
  }
  revision 2022-12-02 {
    description "Editorial";
    yexte:version "1";
    yexte:release "12";
    yexte:correction "2";
    reference "RFC 6733: Diameter Base Protocol";
  }
  revision 2022-09-26 {
    description "Editorial";
    yexte:version "1";
    yexte:release "12";
    yexte:correction "1";
    reference "RFC 6733: Diameter Base Protocol";
  }
  revision 2022-07-01 {
    description "update-message-destination for peer-selector";
    yexte:version "1";
    yexte:release "12";
    yexte:correction "0";
    reference "RFC 6733: Diameter Base Protocol";
  }
  revision 2022-06-28 {
    description "Editorial";
    yexte:version "1";
    yexte:release "11";
    yexte:correction "3";
    reference "RFC 6733: Diameter Base Protocol";
  }
  revision 2022-06-27 {
    description "Editorial";
    yexte:version "1";
    yexte:release "11";
    yexte:correction "2";
    reference "RFC 6733: Diameter Base Protocol";
  }
  revision 2022-06-22 {
    description "Editorial";
    yexte:version "1";
    yexte:release "11";
    yexte:correction "1";
    reference "RFC 6733: Diameter Base Protocol";
  }
  revision 2022-06-08 {
    description "static-peer-group (of peer-selector) extended with
    update-message-destination";
    yexte:version "1";
    yexte:release "11";
    yexte:correction "0";
    reference "RFC 6733: Diameter Base Protocol";
  }
  revision 2022-05-20 {
    description "Editorial";
    yexte:version "1";
    yexte:release "10";
    yexte:correction "2";
    reference "RFC 6733: Diameter Base Protocol";
  }
  revision 2022-04-22 {
    description "Editorial";
    yexte:version "1";
    yexte:release "10";
    yexte:correction "1";
    reference "RFC 6733: Diameter Base Protocol";
  }
  revision 2022-04-05 {
    description "Load regulation (preliminary)";
    yexte:version "1";
    yexte:release "10";
    yexte:correction "0";
    reference "RFC 6733: Diameter Base Protocol";
  }
  revision 2022-02-15 {
    description "Editorial";
    yexte:version "1";
    yexte:release "9";
    yexte:correction "4";
    reference "RFC 6733: Diameter Base Protocol";
  }
  revision 2022-02-11 {
    description "Editorial";
    yexte:version "1";
    yexte:release "9";
    yexte:correction "3";
    reference "RFC 6733: Diameter Base Protocol";
  }
  revision 2022-02-09 {
    description "Editorial";
    yexte:version "1";
    yexte:release "9";
    yexte:correction "2";
    reference "RFC 6733: Diameter Base Protocol";
  }
  revision 2022-01-07 {
    description "Editorial";
    yexte:version "1";
    yexte:release "9";
    yexte:correction "1";
    reference "RFC 6733: Diameter Base Protocol";
  }
  revision 2021-11-29 {
    description "Overload protection";
    yexte:version "1";
    yexte:release "9";
    yexte:correction "0";
    reference "RFC 6733: Diameter Base Protocol";
  }
  revision 2021-11-04 {
    description "Configurable SCTP profile (sctp-profile)";
    yexte:version "1";
    yexte:release "8";
    yexte:correction "0";
    reference "RFC 6733: Diameter Base Protocol";
  }
  revision 2021-07-23 {
    description "Dual-Stack, Selective IP Address to Diameter EP Association";
    yexte:version "1";
    yexte:release "7";
    yexte:correction "0";
    reference "RFC 6733: Diameter Base Protocol";
  }
  revision 2021-03-02 {
    description "SCTP DTLS tls-host-name-validation, security-level";
    yexte:version "1";
    yexte:release "6";
    yexte:correction "0";
    reference "RFC 6733: Diameter Base Protocol";
  }
  revision 2021-02-16 {
    description "DTLS support";
    yexte:version "1";
    yexte:release "5";
    yexte:correction "0";
    reference "RFC 6733: Diameter Base Protocol";
  }
  revision 2021-01-19 {
    description "Message destination validation switch per service";
    yexte:version "1";
    yexte:release "4";
    yexte:correction "0";
    reference "RFC 6733: Diameter Base Protocol";
  }
  revision 2021-01-18 {
    description "Version step";
    yexte:version "1";
    yexte:release "3";
    yexte:correction "2";
    reference "RFC 6733: Diameter Base Protocol";
  }
  revision 2021-01-14 {
    description "Editorial";
    yexte:version "1";
    yexte:release "3";
    yexte:correction "1";
    reference "RFC 6733: Diameter Base Protocol";
  }
  revision 2020-11-06 {
    description "DIA: System-create diameter and
                 change service cardinality constraint";
    yexte:version "1";
    yexte:release "3";
    yexte:correction "0";
    reference "RFC 6733: Diameter Base Protocol";
  }
  revision 2020-10-15 {
    description "DIA, Fast feedback if no connections are available towards
                 Diameter Peer";
    yexte:version "1";
    yexte:release "2";
    yexte:correction "0";
    reference "RFC 6733: Diameter Base Protocol";
  }
  revision 2020-10-05 {
    description "TLS support";
    yexte:version "1";
    yexte:release "1";
    yexte:correction "0";
    reference "RFC 6733: Diameter Base Protocol";
  }
  revision 2020-05-21 {
    description "Alarm information updates";
    yexte:version "1";
    yexte:release "0";
    yexte:correction "3";
    reference "RFC 6733: Diameter Base Protocol";
  }
  revision 2020-05-20 {
    description "Agent role support, predictive-loop-avoidance-enabled added";
    yexte:version "1";
    yexte:release "0";
    yexte:correction "2";
    reference "RFC 6733: Diameter Base Protocol";
  }
  revision 2020-04-20 {
    description "Base for ADP";
    yexte:version "1";
    yexte:release "0";
    yexte:correction "1";
    reference "RFC 6733: Diameter Base Protocol";
  }

  /*********************************************************************/
  container diameter {
    must '( routing-table ) ' { //maybevalue in generated JSON
      error-message "Routing table definition is mandatory.";
      error-app-tag "diameter-routing-table";
    }
    presence "Diameter stack is in use";
    yexte:is-system-created;
    description "Diameter instance represents a singleton entry point in the
    configuration model of the Diameter Service.";
    leaf user-label {
      type string;
      description "Label for free use.";
    }
    /*********************************************************************/
    list service {
      must '( enabled = "false" ) or'
         + '( count( /diameter/routing-table[service= current()/id]) = 1 )' {
        error-message "Each enabled service must have exactly one routing table
        referring to it.";
        error-app-tag "service-routing-table";
      }
      must '( enabled = "false" ) or'
      + '( count ( '
      + '/diameter/transport/node[id=/diameter/transport/local-endpoint'
      + '[id=current()/local-endpoint-reference[enabled="true"]/local-endpoint]'
      + '[enabled="true"]/node] ) = 1 )' {
        error-message "Each enabled local endpoint of an enabled service must
        refer to the same node";
        error-app-tag "service-local-endpoint-node";
      }
      must '( enabled = "false" ) or'
         + '( local-endpoint-reference )' {
        error-message "Enabled service must have at least an endpoint defined.";
        error-app-tag "service-local-endpoint-reference";
      }
      key "id";
      yexte:is-system-created;
      //min-elements 1; 
      //to make parent/root element loadable in itself by the stack
      description "A service instance is used to describe the properties of AAA
        Service implemented by a Diameter Service User. The settings on
        service instance level are influencing the interaction mechanisms
        performed between the Diameter Service and related AAA Service.";
      leaf id {
        type string;
        description "Used to specify the key of the service instance. The
        key value provided should match the name the related AAA Service
        implementation was registering with towards the Diameter Service
        through one of the Diameter Service User interfaces.";
      }
      leaf service-execution-environment {
        type enumeration {
          enum linux {
            value 0;
            description "The AAA Service implementation is executed in the
            context of one or more LINUX process instances.";
          }
          enum dicos {
            value 1;
            description "The AAA Service implementation is executed in the
            context of one or more DICOS process instances.";
          }
        }
        config false;
        description "Used to indicate the execution environment type the
        Diameter Service User is using for AAA Service implementation.";
      }
      leaf ingress-request-pending-timer {
        type uint32;
        units "milliseconds";
        default "5000";
        description "Used to specify the time-out period the Diameter Service
          waits for a AAA Service instance to answer a diameter ingress
          request message. The time-out value provided is interpreted in
          milliseconds. The Diameter Stack will free resources allocated for an
          ingress request message if not answered by AAA Service instance in
          the indicated time-out period. An egress answer message received
          for the related ingress request after the indicated time-out
          period is discarded by the Diameter Service. Each time an egress
          diameter answer message is dropped by the Diameter Stack due to
          the time-out configured through the request-pending-timer, the
          Diameter.EgressAnswMsgDiscarded.TimeOut counter is stepped.
           Unit: millisecond (ms)
           MT Impacted: Diameter.EgressAnswMsgDiscarded.TimeOut
           Update Effect: No impact on established Peer connections. The
           Diameter Service will wait the indicated time-out period for
           diameter answer messages pertaining to newly received diameter
           ingress request messages.";
      }
      leaf egress-request-pending-timer {
        type uint32;
        units "milliseconds";
        default "10000";
        description "Used to specify the time-out period the Diameter Service
          waits for an answer message related to the request message sent by the
          AAA Service instance.
          The egress request message is stored temporarily in the pending queue
          of the Diameter Service for this timeout period. The time-out value
          provided is interpreted in milliseconds.
          The Diameter Stack will free resources allocated for an egress request
          message and step the Diameter.EgressReqMsgDiscarded.TimeOut counter
          if not answered by remote peer in the indicated time-out period.
          Unit: millisecond (ms)
          MT Impacted: Diameter.EgressReqMsgDiscarded.TimeOut
          Update Effect: No impact on established Peer connections.The Diameter
          Service will wait the indicated time-out period for diameter answer
          messages pertaining to newly sent diameter egress request messages. ";
      }
      leaf request-send-max-retry {
        type uint32;
        units "number of retries";
        default "3";
        description "Used to specify the maximum number of times the Diameter
        Service retries to send a diameter egress request message. 
        Egress request message resend can be triggered by the following events:
           Link fail-over
           That is, the active Peer connection is lost and the stack is
           failing over to use as active another Peer connection.
           Time-out
           The time-out specified runtime by the _AAA Service_ implementation
           for the related diameter egress request message expires.
           Diameter answer message
           An answer with result code `DIAMETER_UNABLE_TO_DELIVER (3002)`
           is received.
           Any of the above events should appear the Diameter Service will
           try to resend the egress request messages the indicated amount
           of times. This, however, might be constraint by the number of
           fail-overs Diameter Service can perform upon link loss. That is,
           if there is no link available to send out a request message no
           message caching and retries are performed. Diameter Service will
           indicate related AAA Service instance the inability to deliver
           request messages.
           Each time an egress diameter message is resent the
           Diameter_EgressReqMsgResent_TotalCount counter is stepped.
           NOTE: The connection is excluded for a certain request in case
           of time-out. When an answer with result code `3002` is received
           from a host, all connections towards that host is excluded for
           a certain request. During the retried delivery of the request,
           the next available connection is selected based on the routing
           table but without the excluded connections.
           Unit: Count
           MT Impacted: Diameter.EgressReqMsgResent.TotalCount
           Update Effect: No impact on established Peer connections. Diameter
           Service will apply the newly configured retry count for egress
           request messages stored in message pending queue.";
      }
      leaf request-error-handler {
        type enumeration {
          enum stack {
            value 0;
            description "Faulty diameter ingress request messages are not
            sent towards related AAA Service implementation but handled on
            diameter level.";
          }
          enum service {
            value 1;
            description "Faulty diameter ingress request messages are
            sent towards the related AAA Service implementation by diameter.";
          }
        }
        config false;
        description "Used to indicate the layer the diameter error messages
        are created for related erroneous diameter ingress request messages.";
      }
      leaf request-stack-handler-selection {
        type enumeration {
          enum local {
            value 0;
            description "The compute resource selected for diameter ingress
            request message processing on diameter level is the one handling the
            Peer connection through which the related diameter message
            was received. That is, the diameter ingress request message
            is processed on the same compute resource the message was
            received on.";
          }
          enum cluster {
            value 1;
            description "The compute resource used for diameter ingress request
            message processing on diameter level is determined by using a
            Session-Id AVP based hashing algorithm. If the Session-Id
            AVP is not present in the related diameter request message
            the compute resource is selected in a random way.";
          }
        }
        default "local";
        description "Used to specify the algorithm based on which compute
        resources are selected for diameter ingress request message processing
        on Diameter Service level (that is, for message grammar validation,
        routing entry evaluation and message content based common diameter
        facility activation).
        Wether to use the LOCAL or the CLUSTER compute resource selection
        algorithm should be the result of a dimensioning activity. However,
        if a AAA Service needs no complex message processing activities to
        be performed on diameter level the LOCAL algorithm is recommended
        to be selected. This algorithm will provide better figures both in
        latency and throughput for such type of AAA Services. The default
        CLUSTER compute resource selection algorithm is defined on worst
        case basis (safety margin). Meaning, big diameter cluster with
        few dominant Peer connections with complex message processing
        needs on Diameter Service level (that is, not a typical deployment
        scenario for most of the Diameter Service user AAA Services).
        Update Effect: No impact on established Peer connections. Diameter
        Service will apply the newly configured distribution mechanism
        for message processing.";
      }
      leaf answer-stack-handler-selection {
        type enumeration {
          enum local {
            value 0;
            description "The compute resource selected for diameter ingress
            answer message processing on diameter level is the one handling the
            Peer connection through which the related diameter message
            was received. That is, the diameter ingress answer message
            is processed on the same compute resource the message was
            received on.";
          }
          enum cluster {
            value 1;
            description "The compute resource used for diameter ingress answer
              message processing on diameter level is determined by using
              a Session-Id AVP based hashing algorithm. If the Session-Id
              AVP is not present in the related diameter request message
              the compute resource is selected in a random way.";
          }
        }
        default "local";
        description "Used to specify the algorithm based on which compute
        resources are selected for diameter ingress answer message processing on
        Diameter Stack level (that is, for message grammar validation and
        message content based common diameter facility activation).
        Wether to use the LOCAL or the CLUSTER compute resource selection
        algorithm should be the result of a dimensioning activity.
        However, if a AAA Service needs no complex message processing
        activities to be performed on diameter level the LOCAL algorithm
        is recommended to be selected. This algorithm will provide better
        figures both in latency and throughput for such type of AAA
        Services. The default CLUSTER compute resource selection algorithm
        is defined on worst case basis (safety margin). Meaning, big
        diameter cluster with few dominant Peer connections with complex
        message processing needs on Diameter Service level (that is, not
        a typical deployment scenario for most of the Diameter Service
        user AAA Services).
        Update Effect: No impact on established Peer connections. Diameter
        Service will apply the newly configured distribution mechanism
        for message processing.";
      }
      leaf session-id-format-type {
        type enumeration {
          enum hlbits32 {
            value 0;
            description "The Session-Id AVP will take the format recommended
            by RFC 6733:
            <DiameterIdentity>;<high 32 bits>;<low 32bits>[;<optionalvalue>]";
          }
          enum hlbits64 {
            value 1;
            description "The Session-Id AVP will take the following format
            (also compliant with RFC 6733 defined Session-Id AVP representation
            requirements): 
            <DiameterIdentity>;<high 64 bits>;<low 64bits>[;<optional value>]";
          }
        }
        config false;
        description "Used to indicate one of the different representation
        format types of the generated Session-Id AVP. For detailed information,
        see https://tools.ietf.org/html/rfc6733#section-8.8";
      }
      leaf enabled {
        type boolean;
        default "true";
        description "Used to enable/disable a AAA Service. As result of
        a service disable, all related peer diameter connections will be closed
        with cause indicated by the configured disconnect cause policy.
        When disabled, the following alarm is raised:
        ADP Diameter Managed Object Disabled";
      }
      leaf predictive-loop-avoidance-enabled {
        type boolean;
        default "false";
        config false;
        description "System initialized, used by AAA Services playing
        Relay or Proxy Agent role.
        Predictive loop avoidance shall be enabled by relay or proxy agent, so
        Diameter checks for forwarding loops before forwarding or routing a
        request. See https://tools.ietf.org/html/rfc6733#section-6.1.7";
      }
      leaf fast-feedback-enabled {
        type boolean;
        default "false";
        description "Used to enable/disable fast feedback on user API when no
        connection is available towards the Peers where the egress request
        message could be routed.
        By default, Diameter is waiting egress-request-pending-timer period
        for a Peer connection to come up before sending the Diameter Service
        Users an error indicating no connection.
        If the fast-feedback-enabled is set to true, Diameter sends such
        indication immediatelly.";
      }
      leaf message-destination-validation-enabled {
        type boolean;
        default "true";
        description "Can be used to turn off message destination validation for
        ingress requests.
        If active, before routing the ingress message to a service,
        Destination-Host and Destination-Realm AVPs are matched against the
        actual configuration of the own Diameter Node. In case of a mismatch,
        the message is answered with DIAMETER_UNABLE_TO_DELIVER.
        If turned off, the ingress request is routed to a service even when
        Destination-Host and Destination-Realm AVPs are not matching the actual
        configuration.
        Related https://tools.ietf.org/html/rfc6733#section-6.1.4";
      }
      leaf load-regulation-priority {
        type uint16 {
          range "0..19";
        }
        default "9";
        description "Can be used during load regulation to prioritize diameter
        messages carrying the Application-Id implemented by the service.
        That is, when messages are to be dropped by the stack due to load
        regulation, those having the lowest priority are dropped first.";
      }
      leaf user-label {
        type string;
        description "Label for free use.";
      }
      leaf-list application {
        type leafref {
          path "../../applications/id";
        }
        config false;
        description "Used to indicate the set of Diameter Applications
          (https://tools.ietf.org/html/rfc6733#section-1.3.4) implemented
          by the AAA Service.";
      }
      leaf reroute-policy {
        type leafref {
          path "/diameter/policies/reroute-policy/id";
        }
        description "Reference to a reroute policy";
      }
      action list-peers {
        description "Used to list the Diameter Peers the related Diameter
        Service is in relation with. The resulting Diameter Peer list is scoped
        in accordance with the command argument provided. Dumps a structured
        list of Diameter Peer Origin Hosts.";
        input {
          uses peer-properties;
          leaf host-filter {
            type string;
            default ".*";
            description "Used to express a filter over the Origin-Host of
            the Diameter Peer. By default all hosts are listed.
            It should be expressed as a regular expression
            (eg: node1\\.operator1\\.com, .*\\.operator1\\.com).
            The provided regular expression will be used to search for Diameter
            Peers, with matching Origin-Host, accepted by current 
            dynamic-peer-acceptor.";
          }
        }
        output {
          uses peer-list-information;
        }
      }
      action show-peer {
        description "Used to get status information about the indicated
        Diameter Peer.
        The specified peer-origin-host should refer to a Diameter Node which is
        a peer of the own Diameter Node. Returns a list of connections of
        the indicated Diameter Peer.";
        input {
          leaf peer-origin-host {
            type inet:domain-name;
            mandatory true;
            description "Holds the Origin-Host of the Diameter Peer. Typically,
            one of the Diameter Peers listed with list-peers action.";
          }
        }
        output {
          uses peer-information;
        }
      }
      action list-connections {
        description "Used to list the Peer connections of the indicated
        Diameter Peer.
        Dumps structured information about the Peer connections of
        indicated diameter peer. The specified peer-origin-host should refer
        to a Diameter Node which is a peer of the current Diameter Node.";
        input {
          leaf peer-origin-host {
            type inet:domain-name;
            mandatory true;
            description "Holds the Origin-Host of the Diameter Peer
            information should be exposed about. Typically, one of the Diameter
            Peers listed with list-peers action.";
          }
        }
        output {
          uses connection-list-information;
        }
      }
      action show-connection {
        description "Used to provide information about the indicated diameter
          Peer connection. The specified connection-id should identify a
          connection of the Diameter Node. Dumps structured information
          about the indicated Diameter Peer connection.";
        input {
          leaf connection-id {
            type string;
            mandatory true;
            description "Holds the identity of the Diameter Peer connection
            information is to be provided about. Should hold a connection
            identity in the format returned by the list-connections action.";
          }
        }
        output {
          uses connection-information;
        }
      }
      action kill-connection {
        description "Used to kill the established diameter connection
        identified by connection-id. 
        This asynchronous action is mainly created for troubleshooting purposes:
        One can kill a connection and test system link failover and link
        re-establishment capabilities. By need enforcing diameter link
        re-establishment through another PL node of local Diameter Node can be
        obtained this ways as well in connection termination mode.
        Can only kill connections established towards Peers the related
        service is in connection with.
        Kill operation is not a disable operation. That is, a killed
        connection might be setup again by any of the related nodes (own
        Diameter Node or Peer). Operation success should be checked using action
        list-connections. After killing a connection yet another one can
        be initiated either by th own Node or Peer. One should check
        uptime to realize how recent a Peer connection is.";
        input {
          leaf connection-id {
            type string;
            mandatory true;
            description "Used to indicate the identity of the connection to be
              killed. Should hold a connection identity in the format returned
              by the list-connections action.";
          }
        }
        output {
          uses action-result;
        }
      }
      action kill-all-connections-of-peer {
        description "Used to kill all the established diameter connections
        towards the indicated Peer.
        This asynchronous action is mainly created for troubleshooting
        purposes. One can kill connections to:
        Test Diameter Service link fail-over and link reestablishment
        capabilities.
        Enforce diameter link reestablishment towards another Diameter
        Service Instance in connection termination mode.
        Can specify only those peer-origin-hosts which are in connection
        with actual Diameter Service. Can only be used to kill connections
        established towards Peers of the actual the Diameter Service.
        A kill operation is not a disable operation. That is, a killed
        connection might be setup again by any of the related nodes (own
        Node or Peer). Operation success should be checked using action
        list-connections. After killing a connection yet another one can
        be initiated either by the own Node or Peer. One should check
        uptime to realize how recent a Peer connection is.";
        input {
          leaf peer-origin-host {
            type inet:domain-name;
            mandatory true;
            description "Holds the Origin-Host of the Diameter Peer which
            connections should be killed. Typically, one of the Diameter
            Peers listed with list-peers action.";
          }
        }
        output {
          uses action-result;
        }
      }
      action kill-all-connections {
        description "Used to kill all the Diameter Peer connections of
        the Diameter Service. This asynchronous action is mainly created for
        troubleshooting purposes:
        One can kill connections and test system link failover and link
        re-establishment capabilities.
        By need enforcing diameter link re-establishment through another
        PL node of local Diameter Node can be obtained this ways as well
        in connection termination mode.
        Operation success should be checked using action
        list-connections. After killing a connection yet another one can
        be initiated either by local node or Peer. One should check
        uptime to realize how recent a Peer connection is.";
        output {
          uses action-result;
        }
      }
      action dump-routing-table {
        description "Used to dump a textual, code-style representation of
        the routing table content of the service.";
        output {
          uses action-result;
        }
      }
      /*********************************************************************/
      list local-endpoint-reference {
        key "id";
        description "A local-endpoint-reference instance is used to
        associate an already defined diameter transport local endpoint with a
        AAA Service. A AAA Service can use arbitrary number of transport local
        endpoints. However, all of these endpoints must be associated
        with the same Diameter Node (represented by node). The settings
        on local-endpoint-reference instance level are influencing the way
        the Peer connections associated with a certain transport endpoint
        are handled.";
        leaf id {
          type string;
          description "Used to specify the key of the local-endpoint-reference
          instance.";
        }
        leaf enabled {
          type boolean;
          default "true";
          description "Used to enable or disable the use of the referred
          transport local endpoint for the related AAA Service (that is, it
          disables the related local-endpoint-reference instance).
          true: The use of the referred transport local endpoint is allowed.
          false: The use of the referred transport local endpoint is
          disallowed.
          Disabling a local-endpoint-reference instance will result
          in dropping all the Peer connections established through the
          referred local-endpoint instance between parent AAA Service
          and related Diameter Peers.
          When disabled, the following alarm is raised:
          ADP Diameter Managed Object Disabled
          Update Effect: All established Diameter Peer connections linked
          to referred endpoint are dropped if value set to false.";
        }
        leaf rank {
          type uint32;
          description "Used to express precedence for referred transport
          local endpoint selection during diameter egress request message
          routing. The rank value is considered during diameter egress request
          message routing when references towards multiple transport local
          endpoints are defined for a AAA Service (that is, multiple
          local-endpoint-reference are defined for same AAA Service)
          and the referred transport local endpoints are pointing to either:
          static peers with no connection restriction: Diameter Peers
          represented by dedicated static-peer in the diameter data tree
          with connection amount restriction towards same peer disabled
          (see also restrict-connections of static-peer)
          dynamic peers with or without connection restriction:
          Diameter Peers allowed to connect to the own Diameter Node
          as result of matching conditions expressed through a related
          dynamic-peer-acceptor with or without restriction on connection
          amount (see also restrict-connections of dynamic-peer-acceptor).
          The lowest the value provided the highest the priority assigned
          to the referred endpoint in related AAA Service configuration
          context. That is, the highest priority is assigned to a referred
          transport local endpoint by setting the rank value to 0.
          Multiple local-endpoint-reference instances of a AAA Service
          presenting same rank value and pointing to transport local
          endpoints falling into one of the conditions above defined
          will have equal priority during routing evaluation. That
          is, in such conditions the Diameter Service will perform
          https://tools.ietf.org/html/rfc6733#section-8.8[Session-Id AVP]
          hashing based message load balancing (load sharing) between
          the relevant transport connections. If the
          https://tools.ietf.org/html/rfc6733#section-8.8[Session-Id
          AVP] is not present in the related diameter request message
          connections are selected in random order.
          Update Effect: Depending on configured value a link fail-over
          might be triggered.";
        }
        leaf-list application {
          type leafref {
            path "../../../applications/id";
          }
          description "Used to restrict the use of referred transport
          local endpoint to a limited set of Diameter Applications implemented 
          by the AAA Service. 
          That is, the referred Diameter Applications must be a
          full-set or a sub-set of the Diameter Applications implemented
          by the parent AAA Service. The values shall refer to those
          applications that are allowed to use the referred transport local
          endpoint.
          Update Effect: All established Diameter Peer connections
          linked to related AAA Service are dropped and reestablished
          with updated Diameter Application information.";
        }
        leaf local-endpoint {
          type leafref {
            path "/diameter/transport/local-endpoint/id";
          }
          mandatory true;
          description "Used to specify the reference towards the transport
          local endpoint the AAA Service should use. That is, the relevant
          local-endpoint.";
        }
        leaf user-label {
          type string;
          description "Label for free use.";
        }
      }
    }
    /*********************************************************************/
    list applications {
      key "id";
      yexte:is-system-created;
      description "The instances of applications are used to define
        https://tools.ietf.org/html/rfc6733#section-1.3.4 Diameter
        Applications as defined by the Diameter Base Protocol
        (https://tools.ietf.org/html/rfc6733.
         A AAA Service can implement the client, server or agent side of
         one or several Diameter Applications. The behavior of implemented
         Diameter Applications is defined through related Diameter Application
         Specifications released by different standardization bodies (for
         example: 3GPP, IETF, ETSI, and so on) or vendors (for example:
         Ericsson).";
      leaf id {
        type string;
        description "Used to specify the key of the applications";
      }
      leaf-list auth-application-id {
        type uint32;
        config false;
        description "Used to advertise support of the Authentication and
        Authorization portion of a Diameter Application.";
      }
      leaf-list acct-application-id {
        type uint32;
        config false;
        description "Used to advertise support of the Accounting portion of
        a Diameter Application.";
      }
      leaf-list supported-vendor-id {
        type uint32;
        config false;
        description "Used to advertise support for AVPs defined by vendors
        other than the device vendor but including the application vendor.";
      }
      leaf-list vendor-specific-application-id {
        type leafref {
          path "../../vendor-specific-application-id/id";
        }
        config false;
        description "Used to advertise support of one or more Vendor-Specific
        Diameter Applications represented by related 
        vendor-specific-application-id instances.";
      }
      leaf-list dictionary {
        type leafref {
          path "../../dictionary/id";
        }
        config false;
        min-elements 1;
        description "Used to refer to the Diameter Application Specifications
        of the Diameter Applications advertised by the applications
        instance. A Diameter Application Specification is a dictionary
        holding the grammar of the diameter messages used by a Diameter
        Application. These dictionaries are stored in related dictionary
        instances.";
      }
    }
    /*********************************************************************/
    list vendor-specific-application-id {
      key "id";
      yexte:is-system-created;
      description "A vendor-specific-application-id instance is used to provide
        information about a vendor specific Diameter Application. The
        information provided in a vendor-specific-application-id
        instance is used to construct a Vendor-Specific-Application-Id AVP
        (https://tools.ietf.org/html/rfc6733#section-6.11) which is of type
        grouped. Each of a vendor-specific-application-id instance represents
        a Vendor-Specific-Application-Id AVP. The handling rules defined for
        Vendor-Specific-Application-Id AVP applies for the
        related vendor-specific-application-id instance as well.";
      leaf id {
        type string;
        description "The key of the vendor-specific-application-id instance.";
      }
      leaf vendor-id {
        type uint32;
        config false;
        mandatory true;
        description "Used to indicate the identity of the vendor who might have
          authorship of the Vendor-Specific Diameter Application.";
      }
      leaf auth-application-id {
        type uint32;
        config false;
        description "Used to advertise support of the Authentication and
        Authorization portion of a Vendor-Specific Diameter Application.";
      }
      leaf acct-application-id {
        type uint32;
        config false;
        description "Used in order to advertise support of the Accounting
        portion of a Vendor-Specific Diameter Application.";
      }
      leaf user-label {
        type string;
        description "Label for free use.";
      }
    }
    /*********************************************************************/
    list dictionary {
      key "id";
      yexte:is-system-created;
      description "A dictionary instance is used to store the dictionary of
      a Diameter Application.";
      leaf id {
        type string;
        description "Used to specify the key of the dictionary instance.";
      }
      leaf specification {
        type string;
        config false;
        mandatory true;
        description "Used to load a diameter dictionary.";
      }
    }
    /*********************************************************************/
    container peer-table {
      description "A peer-table system created singleton instance is to be
      used as a container for static-peer and dynamic-peer-acceptor instances
      that are used to scope/filter the Diameter Peers which should be
      considered and stored by the Diameter Service in its internal Peer
      Table.";
      action list-peers {
        description "Used to list the Diameter Peers the related Diameter
        Service is in relation with. 
        The resulting Diameter Peer list is scoped in accordance with the
        command argument provided. Returns a structured list of Diameter Peers
        identified by related Origin-Host.";
        input {
          uses peer-properties;
          leaf host-filter {
            type string;
            default ".*";
            description "Used to express a filter over the Origin-Host of
            the Diameter Peer. By default all hosts are listed.
            It should be expressed as a regular expression
            (eg: node1\\.operator1\\.com, .*\\.operator1\\.com).
            The provided regular expression will be used to search for Diameter
            Peers, with matching Origin-Host, connected to the AAA
            Service.";
          }
        }
        output {
          uses peer-list-information;
        }
      }
      action show-peer {
        description "Used to get status information about the indicated
        Diameter Peer.
        The specified peer-origin-host should refer to a Diameter
        Peer in this peer-table. Typically, a Peer listed by list-peers
        action. Returns structured information about the indicated Diameter
        Peer.";
        input {
          leaf peer-origin-host {
            type inet:domain-name;
            mandatory true;
            description "Holds the Origin-Host of the Diameter Peer. Typically,
            one of the Diameter Peers listed with list-peers action.";
          }
        }
        output {
          uses peer-information;
        }
      }
      action list-connections {
        description "Used to list the Peer connections of the indicated
        Diameter Peer.
        The specified peer-origin-host should refer to a Diameter Peer which is
        a peer of this peer-table. Typically, a peer listed by
        list-peers action.
        Returns a list of connections of the indicated Diameter Peer.";
        input {
          leaf peer-origin-host {
            type inet:domain-name;
            mandatory true;
            description "Holds the Origin-Host of the Diameter Peer. Typically,
            one of the Diameter Peers listed with list-peers action.";
          }
        }
        output {
          uses connection-list-information;
        }
      }
      action show-connection {
        description "Used to get structured information about a diameter
          Peer connection. The ought Diameter Peer connection must be
          identified by a connection-id (as returned by the list-connections
          action). Returns structured information about the indicated diameter
          Peer connection.";
        input {
          leaf connection-id {
            type string;
            mandatory true;
            description "Holds the identity of the Diameter Peer connection
            information is to be provided about. Should hold a connection
            identity in the format returned by the list-connections action.";
          }
        }
        output {
          uses connection-information;
        }
      }
      action kill-connection {
        description "Used to kill the established diameter connection
        identified by connection-id.
        This asynchronous action is mainly created for troubleshooting
        purposes. One can kill a connection to:
        Test Diameter Service link fail-over and link reestablishment
        capabilities.
        Enforce diameter link reestablishment towards another Diameter
        Service Instance in connection termination mode.
        The kill-connection action will not disable a diameter peer
        connection. That is, a killed connection might be setup again by
        any of the related Diameter Nodes (own Node or Peer).
        Operation success should be checked by using the list-connections
        action. One should check uptime to realize how recent a peer
        connection is.";
        input {
          leaf connection-id {
            type string;
            mandatory true;
            description "Holds the identity of the Diameter Peer connection to
            be killed. Should hold a connection identity in the format
            returned by the list-connections action.";
          }
        }
        output {
          uses action-result;
        }
      }
      action kill-all-connections-of-peer {
        description "Used to kill all the Peer connections related to this
        peer-table and established towards the indicated Diameter Peer.
        This asynchronous action is created for troubleshooting
        purposes. One can kill Diameter Peer connections to:
        Test Diameter Service link fail-over and link reestablishment
        capabilities.
        Enforce diameter link reestablishment towards another Diameter
        Service Instance in connection termination mode.
        The kill-all-connections-of-peer action will not disable diameter
        Peer connections. That is, any killed connection might be setup
        again by any of the related Diameter Nodes (own Node or
        Peer).
        Operation success should be checked by using the list-connections
        action. One should check uptime to realize how recent a peer
        connection is.";
        input {
          leaf peer-origin-host {
            type inet:domain-name;
            mandatory true;
            description "Holds the Origin-Host of the Diameter Peer which
            connections should be killed. Typically, one of the Diameter
            Peers listed with list-peers action.";
          }
        }
        output {
          uses action-result;
        }
      }
      action kill-all-connections {
        description "Used to kill all the related Diameter Peer connections
        established.
        This asynchronous action is created for troubleshooting
        purposes. One can kill Diameter Peer connections to:
        Test Diameter Service link fail-over and link reestablishment
        capabilities.
        Enforce diameter link reestablishment towards another Diameter
        Service Instance in connection termination mode.
        The kill-all-connections action will not disable any diameter peer
        connection. That is, any killed connection might be setup again
        by any of the related Diameter Nodes (own Node or Peer).
        Operation success should be checked by using the list-connections
        action. One should check uptime to realize how recent a peer
        connection is.";
        output {
          uses action-result;
        }
      }
      /*********************************************************************/
      list static-peer {
        must '( enabled = "false" ) or (count( '
        + '/diameter/transport/local-endpoint[initiate-connection-to-peer'
        + '= current()/id][enabled = "true"] ) + '
        + 'count( '
        + '/diameter/transport/local-endpoint[terminate-connection-from-peer'
        + '= current()/id][enabled = "true"] ) != 0 ) ' {
          error-message "An enabled static-peer must be referred from a
          local-endpoint";
          error-app-tag "static-peer-local-endpoint";
        }
        must '( enabled = "false" ) or '
        + '( restrict-connections = "true" ) or '
        + '(count( '
        + '/diameter/transport/local-endpoint[terminate-connection-from-peer'
        + '= current()/id][enabled = "true"] ) = 0 ) or '
        + '(max-connection-nr = 0 ) or '
        + '(max-connection-nr >= required-connection-nr)' {
          error-message "Max connection nr must be greater than or equal to the
          required connection nr for enabled static-peer clients with
          restrict-connections = false.";
          error-app-tag "static-peer-connection-nr";
        }
        key "id";
        description "A static-peer instance is used to describe in an explicit
        (static) way a Diameter Peer.
        Explicit specification of a Diameter Peer is mandated when
        the own Diameter Node (represented by a node instance) is expected
        to initiate transport connection setups towards it.
        Explicit specification of a Diameter Peer is optional
        when the Peer is expected to initiate transport connection setups
        towards the own Diameter Node. In such a case the Peer or a matching
        rule set for Peers can be specified by using the more generic
        dynamic-peer-acceptor.
        Changes on static-peer instance level might influence the transport
        connections already established between the own Diameter Node
        and Peer.";
        leaf id {
          type string;
          description "Used to specify the key of the static-peer instance.";
        }
        leaf peer-origin-host {
          type inet:domain-name;
          mandatory true;
          description "Used to specify the origin host of the diameter Peer the
          static-peer instance is meant to represent.
          The value provided for peer-origin-host, if any, is matched against
          the value received in the Origin Host AVP during Peer connection
          establishment (CER/CEA) with a Diameter Peer. If matching fails
          (that is, the connecting or connected Diameter Peer is no the
          expected one), the connection establishment is rejected.
          Update Effect: All established Diameter Peer connections towards
          the Peers matching the static-peer expressed constraints are
          dropped and reestablished by need in accordance with updated
          information.";
        }
        leaf restrict-connections {
          type boolean;
          default "true";
          description "Used to disallow more than one Peer connection between
          the own Diameter Node and the Peer represented by the current
          static-peer.
          The Diameter Base Protocol specifies the use of single active
          connection between Diameter Peers. However, Diameter Nodes
          can be implemented by using a cluster of compute resources
          in which case the use of single Peer connection between such
          Diameter Nodes might be a bottleneck in handling required traffic
          throughput. Typically such Diameter Node implementations provides
          settings through which multiple Diameter Peer connections
          towards same Diameter Peer can be established. The Diameter
          Service provides support for such a functionality which
          can be enabled or disabled towards relevant Peer with the help of
          restrict-connections.
          Update Effect: All established Diameter Peer connections towards
          the peers matching the static-peer expressed constraints are
          dropped and reestablished by need in accordance with updated
          information.";
        }
        leaf enabled {
          type boolean;
          default "true";
          description "Used to enable or disable establishment of peer
          connections with the Diameter Peer(s) the static-peer instance is
          meant to represent.
          When disabled, the following alarm is raised:
          ADP Diameter Managed Object Disabled
          Update Effect: All established Diameter Peer connections towards
          the peers matching the static-peer expressed constraints are
          disconnected upon setting to value false.";
        }
        leaf max-connection-nr {
          type uint32;
          default "4294967295";
          description "Limits the number of connections built from this
          Peer Diameter Node.
          Considered by the Diameter Stack if restrict-connections of the same
          static-peer instance is set to false and the Peer represented by
          static-peer is playing a connection initiation role towards the own
          Diameter Node (that is, the static-peer is referred by a
          local-endpoint through a terminate-connection-from-peer reference).
          0 == Any number, that is the number of connections is not
          limited hereby. See also restrict-connections.";
        }
        leaf required-connection-nr {
          type uint32;
          default "1";
          description "Used to indicate a threshold for the number of redundant
          connections towards the Diameter Peer. When the configured threshold
          is crossed, one of the following alarms is raised:
           ADP Diameter Peer connection Number Below Required Level
           ADP Diameter Peer Unavailable
          Update Effect: When set, the configured threshold will be used by the
          stack during alarm handling.";
        }
        leaf congestion-handling-policy {
          type leafref {
            path "/diameter/policies/congestion-handling-policy/id";
          }
          description "Reference to a congestion-handling policy";
        }
        leaf user-label {
          type string;
          description "Label for free use.";
        }
        action list-connections {
          description "Used to list the Peer connections of the related
          Diameter Peer represented by this static-peer.
          Dumps structured information about the Peer connections of indicated
          Diameter Peer.";
          output {
            uses connection-list-information;
          }
        }
        action show-connection {
          description "Used to get structured information about a diameter peer
            connection. The ought Diameter Peer connection must be identified
            by a connection-id (as returned by the list-connections
            action). Returns structured information about the indicated
            Diameter Peer connection.";
          input {
            leaf connection-id {
              type string;
              mandatory true;
              description "Holds the identity of the Diameter Peer connection
              information is to be provided about. Should hold a connection
              identity in the format returned by the list-connections action.";
            }
          }
          output {
            uses connection-information;
          }
        }
        action kill-connection {
          description "Used to kill the established diameter connection
          identified by connection-id.
          This asynchronous action is mainly created for troubleshooting
          purposes. One can kill a connection to:
          test system link failover and link re-establishment capabilities.
          By need enforcing diameter link re-establishment through another
          PL node of local Diameter Node can be obtained this ways as
          well in connection termination mode.
          Can only kill connections established towards the related
          Diameter Peer represented by the static-peer.
          Kill operation is not a disable operation. That is, a killed
          connection might be setup again by any of the related peers
          (own Node or Peer). Operation success should be checked using
          action list-connections. After killing a connection yet another
          one can be initiated either by local node or Peer. One
          should check uptime to realize how recent a Peer connection is.";
          input {
            leaf connection-id {
              type string;
              mandatory true;
              description "Holds the identity of the Diameter Peer connection
              to be killed. Should hold a connection identity in the format
              returned by the list-connections action.";
            }
          }
          output {
            uses action-result;
          }
        }
        action kill-all-connections {
          description "Used to kill all the Diameter Peer connections of
          the related Diameter Peer represented by this static-peer.
          This asynchronous action is mainly created for troubleshooting
          purposes:
          One can kill connections and test system link failover and link
          re-establishment capabilities.
          By need enforcing diameter link re-establishment through another
          PL node of local Diameter Node can be obtained this ways as
          well in connection termination mode.
          Operation success should be checked using action
          list-connections. After killing a connection yet another one
          can be initiated either by own Diameter Node or Peer. One should
          check uptime to realize how recent a Peer connection is.";
          output {
            uses action-result;
          }
        }
        /*********************************************************************/
        list remote-endpoint {
          must '( enabled = "false" ) or (count( '
          + '/diameter/transport/local-endpoint[initiate-connection-to-peer'
          + '= current()/../id][enabled = "true"]) != 0 and address) or (count('
          + '/diameter/transport/local-endpoint[initiate-connection-to-peer'
          + '= current()/../id][enabled = "true"] ) = 0)' {
            error-message "An enabled static-peer server configured as
            initiate-connection-to-peer from a local-endpoint must have its
            address specified";
            error-app-tag "remote-endpoint-address";
          }
          key "id";
          description "A remote-endpoint instance is used to specify a
          remote endpoint for a Diameter Peer represented by the parent
          static-peer instance.
          Many remote endpoints can be defined by need for a Diameter Peer.
          It is mandatory to define at least a remote endpoint if the own
          Diameter Node is configured to initiate connections towards the
          related Peer. If the Peer is the one initiating connections towards
          the own Diameter Node the specification of a remote endpoint can be
          omitted for related Peer.";
          leaf id {
            type string;
            description "Used to specify the key of the remote-endpoint
            instance.";
          }
          leaf-list address {
            type inet:ip-address;
            description "Used to specify the list of IP addresses (IPv4
            or IPv6 addresses) of the remote endpoint that can be used by the
            own Diameter Node to connect to a Diameter Peer (that is acting as
            diameter server, represented by parent static-peer instance).
            The address should take as value a single IP addresses if the
            transport protocol to be used is configured to TCP (see also
            the transport-protocol below). The address can take as value
            multiple IP addresses if the transport protocol to be used
            is configured to SCTP. In such a case the use of combined
            IPv4 and IPv6 addresses is allowed as well.
            When configured Peer acts as diameter client, the specified values
            are used to restrict connection attempts from specified addresses
            only. Only when Kubernetes externalTrafficPolicy is set to 'Local',
            moreover ECFE can communicate using BGP with the FE gateway router,
            the external IP address of the Peer could be configured hereby. In
            opposite to this, when Kubernetes externalTrafficPolicy is set to
            'Cluster', due to the applied SNAT only the worker local address is
            received by Diameter, hence the usage of 
            static-peer/remote-endpoint/address representing a client Peer is
            not recommended in such setups.
            Update Effect: All established Diameter Peer connections
            towards the remote endpoint represented by the related
            remote-endpoint instance are dropped and reestablished with
            updated information.";
          }
          leaf port {
            type inet:port-number;
            default "3868";
            description "Used to specify the port number of the remote
            endpoint that can be used by the own Diameter Node to connect to a
            Diameter Peer (represented by parent static-peer instance).
            The port number specified is valid for all the addresses specified
            for the related local-endpoint instance.
            It has no effect on configured Peers acting as clients.
            Update Effect: All established Diameter Peer connections towards
            the remote endpoint represented by the remote-endpoint instance
            are dropped and reestablished with updated information.";
          }
          leaf transport-protocol {
            type enumeration {
              enum tcp {
                value 0;
                description "Transport protocol TCP.";
              }
              enum sctp {
                value 1;
                description "Transport protocol SCTP.";
              }
            }
            default "tcp";
            description "Used to specify the transport protocol of the
            remote endpoint that can be used by the own Diameter Node when
            initiating Diameter Peer connections.";
          }
          leaf enabled {
            type boolean;
            default "true";
            description "Used to enable or disable the remote endpint of
            the Diameter Peer represented by the parent static-peer.
            When disabled, the following alarm is raised:
            ADP Diameter Managed Object Disabled
            Update Effect: All established Diameter Peer connections towards
            the remote endpoint represented by the related remote-endpoint
            instance are disconnected upon setting to value false.";
          }
          leaf user-label {
            type string;
            description "Label for free use.";
          }
        }
      }
      /*********************************************************************/
      list dynamic-peer-acceptor {
        must '( enabled = "false" ) or (count('
        + '/diameter/transport/local-endpoint'
        + '[terminate-connection-from-accepted-peers=current()/id]'
        +'[enabled="true"]) != 0)' {
          error-message "An enabled dynamic-peer-acceptor must be referred from
          a local-endpoint";
          error-app-tag "dynamic-peer-acceptor-local-endpoint";
        }
        must '( enabled = "false" ) or '
        + '( restrict-connections = "true" ) or '
        + '( (max-peer-connection-nr >= required-connection-nr) and '
        + '(max-connection-nr >= max-peer-connection-nr) )' {
          error-message "max-peer-connection-nr >= required-connection-nr for
          enabled dynamic-peer-acceptors with restrict-connections = false,
          moreover max-connection-nr >= max-peer-connection-nr.";
          error-app-tag "static-peer-connection-nr";
        }
        key "id";
        description "A dynamic-peer-acceptor instance is used to describe the
        conditions based on which Peer connection setups initiated by
        one or a collection of Diameter Peers are to be accepted or
        rejected by own Diameter Node.
        The Diameter Peer identifiers (like peer host IP address, origin host or
        origin realm) are matched against the related value matching patterns
        expressed in a dynamic-peer-acceptor instance. If matching is found
        towards all the expressed patterns the initiated Peer connection is
        accepted by diameter. Otherwise, the remote Peer connection initiation
        is rejected.
        Changes on dynamic-peer-acceptor instance level might influence
        all the Peer connections already established as result of matching
        towards the patterns expressed in related Peer connection acceptor
        instance.
        Note, there is no TLS hostname validation for dynamic Peers.";
        leaf id {
          type string;
          description "Used to specify the key of the dynamic-peer-acceptor
          instance.";
        }
        leaf-list peer-origin-realm {
          type string;
          description "Used to specify the Origin Realm (see
            https://tools.ietf.org/html/rfc6733#section-6.4) validation
            pattern of the Diameter Peers allowed to initiate connections
            towards the own Diameter Node. The provided value shall be either
            a concrete or a pattern based representation (expressed using
            Perl Compatible Regular Expressions, see https://www.pcre.org/)
            of the Origin Realm used by Diameter Peers allowed to connect
            towards the own Diameter Node. The Origin Realm is a Diameter
            Identity (see https://tools.ietf.org/html/rfc6733#section-4.3.1)
            data type as defined by the Diameter Base Protocol, see Diameter
            Base Protocol (RFC 6733) IETF: STANDARD.";
        }
        leaf-list peer-origin-host {
          type string;
          description "Used to specify the Origin Host (see
            https://tools.ietf.org/html/rfc6733#section-6.5) validation
            pattern of the Diameter Peers allowed to initiate connections
            towards the own Diameter Node.
            The provided value shall be either a concrete or a pattern
            based representation (expressed using Perl Compatible Regular
            Expressions, see https://www.pcre.org/) of the Origin Host
            used by Diameter Peers allowed to connect towards the
            own Diameter Node. The Origin Host is a Diameter Identity (see
            https://tools.ietf.org/html/rfc6733#section-4.3.1) data type
            as defined by the Diameter Base Protocol, see Diameter Base
            Protocol (RFC 6733) IETF: STANDARD.";
        }
        leaf-list peer-host-ip-address {
          type string;
          description "Used to specify the Host IP Address (see
            https://tools.ietf.org/html/rfc6733#section-5.3.5) validation
            pattern of the Diameter Peers allowed to initiate connections
            towards the own Diameter Node. The provided value shall be either
            a concrete or a pattern based representation (expressed using
            Perl Compatible Regular Expressions, see https://www.pcre.org/)
            of the Host IP Address used by Diameter Peers allowed to
            connect towards the own Diameter Node. The Host IP Address
            (see https://tools.ietf.org/html/rfc6733#section-4.3.1) is an
            Address data type as defined by the Diameter Base Protocol,
            see Diameter Base Protocol (RFC 6733) IETF: STANDARD.
            Only when Kubernetes externalTrafficPolicy is set to 'Local',
            moreover ECFE can communicate using BGP with the FE gateway router,
            the external IP address of the Peer could be configured hereby. In
            opposite to this, when Kubernetes externalTrafficPolicy is set to
            'Cluster', due to the applied SNAT only the worker local address is
            received by Diameter, hence the usage of peer-host-ip-address is
            not recommended in such setups.";
        }
        leaf-list excluded-host {
          type string;
          description "Defines an Origin Host validation pattern used to
          filter out Diameter Peers that are not allowed to initiate connections
          towards the own Diameter Node.
          Serves as exclude-list expression over the include-list defined
          by peer-origin-host.";
        }
        leaf restrict-connections {
          type boolean;
          default "true";
          description "Used to disallow the establishment of more than
          one Diameter Peer connection from the same Diameter Peer.
          The Diameter Base Protocol specifies the use of single active
          connection between Diameter Peers (see, Diameter Base
          Protocol (RFC 6733) IETF: STANDARD).
          However, Diameter Nodes can be implemented using a cluster of
          compute resources in which case the use of single Peer connection
          between such Diameter Nodes might be a bottleneck in handling
          required traffic throughput. Such Diameter Node implementations
          provides settings through which multiple Diameter Peer connections
          towards same Diameter Peer can be established. diameter provides
          support for such a functionality as well.
          Update Effect: All established Diameter Peer connections
          towards the peers matching the dynamic-peer-acceptor expressed
          constraints are dropped and reestablished by need in accordance
          with updated information.";
        }
        leaf max-peer-connection-nr {
          type uint32;
          default "4294967295";
          description "Sets the maximum number of connections to be accepted
          from a single Diameter Peer. That is, from a peer matching the
          constraints expressed by the actual dynamic-peer-acceptor. In
          case the max-peer-connection-nr value is set to 0 the related
          dynamic-peer-acceptor will behave as a blocker. That is, no
          connections will be allowed from the diameter peers matching
          the filtering conditions expressed by the dynamic-peer-acceptor.
          Considered by the Diameter Service if restrict-connections of the same
          dynamic-peer-acceptor is set to false.
          Update Effect: If the updated value of max-peer-connection-nr is less
          than the previously set one, existing connections will be dropped to
          conform to the newly configured limit.";
        }
        leaf max-connection-nr {
          type uint32;
          default "4294967295";
          description "Used to configure the maximum number of connections
          to be accepted from Diameter Peers matching the constraints expressed
          by the current dynamic-peer-acceptor. This is a value to be
          considered for all Diameter Peers accepted by the current
          dynamic-peer-acceptor and not a value representing individual
          connections per Diameter Peer (see also max-peer-connection-nr
          for connection number constraints per Diameter Peer).
          In case the max-connection-nr is set to 0 the related
          dynamic-peer-acceptor will behave as a blocker. That is, no connection
          establishment will be allowed from any of the Peers matching
          the constraints expressed hereby.
          Considered by the Diameter Service if restrict-connections of the same
          dynamic-peer-acceptor is set to false.
          Update Effect: If the updated value of max-connection-nr is less than
          the previously set one, existing connections will be dropped to
          conform to the newly configured limit.";
        }
        leaf required-connection-nr {
          type uint32;
          default "1";
          description "Used to indicate a threshold for the number of redundant
          connections towards a Diameter Peer. When the configured threshold is
          crossed, but there is at least one active connection available towards
          the Peer, the following alarms is raised:
          ADP Diameter Peer connection Number Below Required Level
          Update Effect: When set, the configured threshold will be used by the
          stack during alarm handling.";
        }
        leaf enabled {
          type boolean;
          default "true";
          description "Used to enable or disable establishment of peer
          connections initiated by Diameter Peer(s) matching the different
          identity validation patterns as expressed by relevant
          dynamic-peer-acceptor instance.
          When disabled, the following alarm is raised:
          ADP Diameter Managed Object Disabled
          Update Effect: All established Diameter Peer connections towards
          the Peers matching the dynamic-peer-acceptor expressed constraints
          are disconnected upon setting to value false.";
        }
        leaf congestion-handling-policy {
          type leafref {
            path "/diameter/policies/congestion-handling-policy/id";
          }
          description "Reference to a congestion-handling policy";
        }
        leaf user-label {
          type string;
          description "Label for free use.";
        }
        action list-peers {
          description "Used to list the Diameter Peers with established
          Diameter Peer connections accepted by current dynamic-peer-acceptor.
          The resulting Diameter Peer list is scoped in accordance with
          the command argument provided. Returns a structured list of Diameter
          Peers identified by related Origin-Host.";
          input {
            leaf host-filter {
              type string;
              default ".*";
              description "Used to express a filter over the Origin-Host of
              the Diameter Peer. By default all hosts are listed.
              It should be expressed as a regular expression 
              (eg: node1\\.operator1\\.com, .*\\.operator1\\.com).
              The provided regular expression will be used to search for
              Diameter Peers, with matching Origin-Host, accepted by current
              dynamic-peer-acceptor.";
            }
          }
          output {
            uses peer-list-information;
          }
        }
        action show-peer {
          description "Used to provide available information about the
          indicated Diameter Peer. The specified peer-origin-host should
          refer to a Diameter Node accepted by the related acceptor listed by
          list-peers. Returns structured information about the indicated
          Diameter Peer.";
          input {
            leaf peer-origin-host {
              type inet:domain-name;
              mandatory true;
              description "Used to set the peer OriginHost information. Should
              refer to a Diameter Node accepted by this acceptor";
            }
          }
          output {
            uses peer-information;
          }
        }
        action list-connections {
          description "Used to list the Peer connections of the indicated
          Diameter Peer accepted by this dynamic acceptor instance. The
          specified peer-origin-host should refer to a Diameter Node which
          is a peer of the own Diameter Node and accepted by this
          acceptor. Returns structured information about the indicated
          Diameter Peer connection.";
          input {
            leaf peer-origin-host {
              type inet:domain-name;
              mandatory true;
              description "Used to set the peer OriginHost information. Should
              refer to a Diameter Node which is a peer of the own Diameter Node
              and accepted by this acceptor.";
            }
          }
          output {
            uses connection-list-information;
          }
        }
        action show-connection {
          description "Used to provide information about the indicated diameter
            Peer connection. The specified connection-id should identify a
            connection of the Diameter Node accepted by this acceptor. Returns
            structured information about the indicated diameter peer
            connection.";
          input {
            leaf connection-id {
              type string;
              mandatory true;
              description "Used to indicate the identity of the relevant
              Diameter Peer connection.";
            }
          }
          output {
            uses connection-information;
          }
        }
        action kill-connection {
          description "Used to kill the established diameter connection
          identified by connection-id.
          This asynchronous action is mainly created for troubleshooting
          purposes. One can kill a connection to:
          Test Diameter Service link fail-over and link reestablishment
          capabilities.
          Enforce diameter link reestablishment towards another Diameter
          Service Instance in connection termination mode.
          Can only kill connections established by the related acceptor
          instance.
          Kill operation is not a disable operation. That is, a killed
          connection might be setup again by any of the related nodes
          (own Node or Peer). Operation success should be checked using
          action list-connections. After killing a connection yet another
          one can be initiated either by own Node or Peer. One
          should check uptime to realize how recent a Peer connection is.";
          input {
            leaf connection-id {
              type string;
              mandatory true;
              description "Used to indicate the identity of the connection
              to be killed. The identity of a connection towards a Peer can be
              obtained with show-peer action performed for relevant peer.";
            }
          }
          output {
            uses action-result;
          }
        }
        action kill-all-connections-of-peer {
          description "Used to kill all the established diameter connections
          towards the indicated Peer accepted by this acceptor.
          This asynchronous action is mainly created for troubleshooting
          purposes. One can kill a connection to:
          Test Diameter Service link fail-over and link reestablishment
          capabilities.
          Enforce diameter link reestablishment towards another Diameter
          Service Instance in connection termination mode.
          Can specify only those peer-origin-hosts which are accepted by
          this acceptor instance.
          A kill operation is not a disable operation. That is, a killed
          connection might be setup again by any of the related nodes
          (own Node or Peer). Operation success should be checked using
          action list-connections. After killing a connection yet another
          one can be initiated either by own Node or Peer. One
          should check uptime to realize how recent a Peer connection is.";
          input {
            leaf peer-origin-host {
              type inet:domain-name;
              mandatory true;
              description "Used to indicate the peer OriginHost towards
              which established connections should be killed.";
            }
          }
          output {
            uses action-result;
          }
        }
        action kill-all-connections {
          description "Used to kill all the Diameter Peer connections accepted
          by this acceptor instance.
          This asynchronous action is mainly created for troubleshooting
          purposes. One can kill a connection to:
          Test Diameter Service link fail-over and link reestablishment
          capabilities.
          Enforce diameter link reestablishment towards another Diameter
          Service Instance in connection termination mode.
          Operation success should be checked using action
          list-connections. After killing a connection yet another one
          can be initiated either by local node or Peer. One should
          check uptime to realize how recent a Peer connection is.";
          output {
            uses action-result;
          }
        }
      }
    }
    /*********************************************************************/
    container transport {
      must '( node )' { //maybevalue in generated JSON
        error-message "Representation of own Diameter Node is mandatory.";
        error-app-tag "transport-node";
      }
      must '( host-address-resolver )' { //maybevalue in generated JSON
        error-message "Address resolver is mandatory to define.";
        error-app-tag "transport-host-address-resolver";
      }
      must '( local-endpoint )' { //maybevalue in generated JSON
        error-message "Endpoint definition is mandatory.";
        error-app-tag "transport-local-endpoint";
      }
      description "A transport instance is a system created singleton
      object instance in the diameter configuration and it is used as a
      container for transport configuration.
      To have the own Diameter Node accept connections from or initiate
      connections towards Diameter Peer, data nodes of the transport
      subtree is to be configured accordingly. This
      is performed by creating one or more Local Endpoints with wanted
      roles and transport capabilities. Local Endpoints are specified
      with instances of local-endpoint.";
      /*********************************************************************/
      list node {
        key "id";
        unique "origin-host";
        description "A node instance is used to specify an own Diameter Node.
        A Diameter Service deployment, on a certain target system, can
        expose/represent arbitrary number of Diameter Nodes (each of them
        expressed by related node instance). The different AAA Service
        implementations using the Diameter Service can be connected to
        relevant Diameter Nodes.
        Any changes on the node instance are applied immediately on Diameter
        Service level. Since all the values provides common content for diameter
        messages used for Diameter Peer connection setup (CER/CEA messages) and
        some subsequent messages, changes on related values will have as result
        the drop of all related Diameter Peer connections and reestablishment
        with updated information. The Diameter Service level queued egress
        request messages will be resent to relevant Diameter Peers.";
        leaf id {
          type string;
          description "Used to specify the key of the node instance.";
        }
        leaf origin-realm {
          type inet:domain-name;
          mandatory true;
          description "Used to specify the origin realm of the Diameter
          Node represented by the node instance.
          The provided value is to be expressed by complying to the Diameter
          Identity (https://tools.ietf.org/html/rfc6733#section-4.3.1)
          data type expression rules as defined by the Diameter Base
          Protocol. The provided value is used to construct a Origin-Realm
          AVP (https://tools.ietf.org/html/rfc6733#section-6.4) which is
          placed in capability exchange messages (CER/CEA messages) during
          related own Diameter Node linked Peer connection establishment.
          Update Effect: All established Diameter Peer connections linked
          to related own Diameter Node are dropped and reestablished with
          updated information.";
        }
        leaf origin-host {
          type inet:domain-name;
          mandatory true;
          description "Used to specify the origin host of the Diameter
          Node represented by the node instance.
          The provided value is to be expressed by complying to the Diameter
          Identity (https://tools.ietf.org/html/rfc6733#section-4.3.1)
          data type expression rules as defined by the Diameter Base
          Protocol. The provided value is used to construct a Origin-Host
          AVP
          (https://tools.ietf.org/html/rfc6733#section-6.3) which is
          placed in capability exchange messages (CER/CEA messages)
          during related AAA Service linked Peer connection setup.
          The provided value must be unique in the context of the related origin
          realm.
          Update Effect: All established Diameter Peer connections linked
          to related own Diameter Node are dropped and reestablished with
          updated information.";
        }
        leaf product-name {
          type string;
          mandatory true;
          description "Used to specify the name of the product behind the
          Diameter Node implementing different AAA Services by using the 
          diameter stack (for example, EIR, SAPC, IpWorks, MTAS, CSCF, HSS).
          The provided value is used to construct a Product-Name AVP
          (https://tools.ietf.org/html/rfc6733#section-5.3.7) placed in
          related capability exchange messages (CER/CEA messages) during
          Peer connection setup.
          The provided product name should remain constant across firmware
          revisions for the same product (see also firmware-revision).
          Update Effect: All established Diameter Peer connections linked
          to related own Diameter Node are dropped and reestablished with
          updated information.";
        }
        leaf vendor-id {
          type uint32;
          default "193";
          description "Used to specify the identity of the vendor implementing
          the product specified for product-name.
          The should take as value an IANA allocated SMI Network Management
          Private Enterprise Code (see
          https://www.iana.org/assignments/enterprise-numbers/enterprise-numbers
          ) assigned for the vendor implementing the product specified for
          product-name.
          Unless the product developer center is not registered with own
          vendor identity one should use the value 193 assigned to Ericsson
          AB. The provided value is used to construct a Vendor-Id AVP
          (https://tools.ietf.org/html/rfc6733#section-5.3.3) placed in
          related capability exchange messages (CER/CEA messages) during
          Peer connection setup.
          Update Effect: All established Diameter Peer connections linked
          to related own Diameter Node are dropped and reestablished with
          updated information.";
        }
        leaf firmware-revision {
          type uint32;
          description "Used to specify the revision of the software product
          specified for product-name.
          If there is an value provided it is
          used to construct a Firmware-Revision AVP
          (https://tools.ietf.org/html/rfc6733#section-5.3.4) placed in
          related capability exchange messages (CER/CEA messages) during
          Peer connection setup.
          Update Effect: All established Diameter Peer connections linked
          to related own Diameter Node are dropped and reestablished with
          updated information.";
        }
        leaf-list host-ip-address {
          type inet:ip-address;
          description "Used to specify the list of IP addresses (a list of
          IPv4 and/or IPv6 addresses) that can be used by a Diameter Peer to
          connect to the own Diameter Node. The IP addresses specified shall
          visible for related Diameter Peers (for instance the IP address of
          external IP load balancer behind which the own Diameter Node is
          placed or alternatively the SENP VIP address).
          The provided values are used to construct relevant Host-IP-Address
          AVP (https://tools.ietf.org/html/rfc6733#section-5.3.5) which
          is placed in capability exchange messages (CER/CEA messages)
          during related AAA Service linked Peer connection setup.
          If no value is provided, the Host-IP-Address AVP is
          constructed by using the IP addresses provided for the own
          Diameter Node related Local Endpoints (see local-endpoint).
          Update Effect: All established Diameter Peer connections linked
          to related own Diameter Node are dropped and reestablished with
          updated information.";
        }
        leaf user-label {
          type string;
          description "Label for free use.";
        }
        list tls-profile {
          if-feature "ks:keystore-supported and ts:truststore-supported";
          nacm:default-deny-write;
          key id;
          description "TLS profile to be associated with local-endpoints of
          the node. Properties of tls-profile are used when securing connections
          for TCP transports with TLS 1.2 or TLS 1.3.";
          leaf id {
              type string;
              description "Used to specify the key of the tls-profile
              instance.";
          }
          container keystore-reference {
            uses ks:asymmetric-key-certificate-ref-grouping {
              refine asymmetric-key {
                mandatory true;
              }
              refine certificate {
                mandatory true;
              }
            }
            description "Reference to a Diameter specific certificate and its
            associated private key in the keystore, but only those printed by
            action show-deployed-certificates can be referenced.
            TLS host name validation in Diameter Peer may require using a
            certificate where included subject alternative name is matching the
            originHost of the Diameter Own Node (see node origin-host).
            Update Effect: All established Diameter Peer connections linked
            to related tls-profile are dropped and reestablished with
            updated information.";
          }
          leaf truststore-reference {
            type ts:certificates-ref;
            description "Reference to a set of Diameter trust anchors that
              exists in the truststore, but only those printed by action
              show-deployed-certificates can be referenced.
              These optional trusts are used when authenticating the Peer.
              Update Effect: All established Diameter Peer connections linked
              to related tls-profile are dropped and reestablished with
              updated information.";
          }
          // Until ietf-tls-common is not deployed by YP or available in EYang
          // define local copies that will be deprecated later
          leaf tls-local-version {
            type enumeration {
              enum tls-1_2-tls-1_3 {
                value 0;
                description "Both TLS 1.2 and TLS 1.3 are supported";
              }
              enum tls-1_3-only { //Hardening
                value 1;
                description "Only TLS 1.3 is supported";
              }
            }
            default tls-1_2-tls-1_3; //BC with older systems
            description "Specifies the supported TLS versions.
              Only TLS 1.2 or newer is allowed for Diameter, while TLS 1.3 must
              always be supported.
              Hardening procedure can switch to TLS 1.3 only.
              Update Effect: All established Diameter Peer connections linked
              to related tls-profile are dropped and reestablished with
              updated information.";
          }
          leaf-list tls-1_2-local-cipher-list {
            when "../tls-local-version = 'tls-1_2-tls-1_3'";//tls-1.2,too
            type tls-1_2-local-cipher-list-enum;
            default "ecdhe-rsa-with-aes-128-gcm-sha256";
            default "ecdhe-rsa-with-aes-256-gcm-sha384";
            default "ecdhe-ecdsa-with-aes-128-gcm-sha256";
            default "ecdhe-ecdsa-with-aes-256-gcm-sha384";
            description "Specifies the list of ciphers for TLS 1.2 based on
            ietf-tls-common. Due to TLS 1.2 being the minimum supported protocol
            version, some of the hereby listed ciphers can not be used.
            If a cipher excluded by RFC7540 is configured, alarm
            DIA Diameter Transport Vulnerability is raised for the related
            tls-profile.
            Chosen ciphers must match the deployed certificate.
            Update Effect: All established Diameter Peer connections linked
            to related tls-profile are dropped and reestablished with
            updated information.";
            reference "https://www.openssl.org/docs/man1.1.1/man1/ciphers.html,
              https://tools.ietf.org/html/rfc7540#appendix-A";
          }
          //until ietf-tls-common does not define 1.3 cipher suites
          leaf-list tls-1_3-local-cipher-suites { //TLS 1.3 always
            type enumeration {
              enum tls-aes-256-gcm-sha384 {
                value 0;
                description "TLS_AES_256_GCM_SHA384";
              }
              enum tls-chacha20-poly1305-sha256 {
                value 1;
                description "TLS_CHACHA20_POLY1305_SHA256";
              }
              enum tls-aes-128-gcm-sha256 {
                value 2;
                description "TLS_AES_128_GCM_SHA256";
              }
              //some (less preferable but still secure) ccm cipher suites 
              enum tls-aes-128-ccm-sha256 {
                value 3;
                description "TLS_AES_128_CCM_SHA256";
              }
              enum tls-aes-128-ccm-8-sha256 {
                value 4;
                description "TLS_AES_128_CCM_8_SHA256";
              }
            }
            default "tls-aes-256-gcm-sha384";
            default "tls-chacha20-poly1305-sha256";
            default "tls-aes-128-gcm-sha256";
            description "Specifies the cipher suites for TLS 1.3 in
              order of preference.
              Update Effect: All established Diameter Peer connections linked
              to related tls-profile are dropped and reestablished with
              updated information.";
            reference "https://www.openssl.org/docs/man1.1.1/man1/ciphers.html";
          }
          leaf security-level {
            type uint16 {
              range "3..5";
            }
            default 3;
            description "Specifies the TLS security level used with this
            profile.
            Hardening procedure can increase the applied security level.
            Level 3
            Security level set to 128 bits of security. As a result RSA, DSA and
            DH keys shorter than 3072 bits and ECC keys shorter than 256 bits
            are prohibited. In addition to the level 2 exclusions cipher suites
            not offering forward secrecy are prohibited. TLS versions below 1.1
            are not permitted. Session tickets are disabled.
            Level 4
                Security level set to 192 bits of security. As a result RSA, DSA
                and DH keys shorter than 7680 bits and ECC keys shorter than 384
                bits are prohibited. Cipher suites using SHA1 for the MAC are
                prohibited. TLS versions below 1.2 are not permitted.
            Level 5
                Security level set to 256 bits of security. As a result RSA, DSA
                and DH keys shorter than 15360 bits and ECC keys shorter than
                512 bits are prohibited.
            Update Effect: All established Diameter Peer connections linked
            to related tls-profile are dropped and reestablished with
            updated information.";
            reference "https://www.openssl.org/docs/man1.1.1/man3/
              SSL_CTX_set_security_level.html";
          }
          leaf user-label {
            type string;
            description "Label for free use.";
          }
        }
        list dtls-profile {
          if-feature "ks:keystore-supported and ts:truststore-supported";
          nacm:default-deny-write;
          key id;
          description "DTLS profile to be associated with SCTP local-endpoints
          of the node. Properties of dtls-profile are used when securing
          connections for SCTP transports with DTLS 1.2.. DTLS protocol is based
          on the Transport Layer Security (TLS) protocol and provides equivalent
          security guarantees. See more at
          https://www.rfc-editor.org/rfc/rfc6347.html
          Properties defined here are passed to the SCTP Service.";
          leaf id {
              type string;
              description "Used to specify the key of the dtls-profile
              instance.";
          }
          container keystore-reference {
            uses ks:asymmetric-key-certificate-ref-grouping {
              refine asymmetric-key {
                mandatory true;
              }
              refine certificate {
                mandatory true;
              }
            }
            description "Reference to a Diameter specific certificate and its
            associated private key in the keystore, but only those printed by
            action show-deployed-certificates can be referenced.
            TLS host name validation in Diameter Peer may require using a
            certificate where included subject alternative name is matching the
            originHost of the Diameter Own Node (see node origin-host).
            Update Effect: All established Diameter Peer connections linked to
            related dtls-profile are dropped and reestablished with updated
            information.";
          }
          leaf truststore-reference {
            type ts:certificates-ref;
            description "Reference to a set of Diameter trust anchors that
            exists in the truststore, but only those printed by action
            show-deployed-certificates can be referenced.
            These optional trusts are used when authenticating the Peer.
            Update Effect: All established Diameter Peer connections linked to
            related dtls-profile are dropped and reestablished with updated
            information.";
          }
          leaf-list tls-1_2-local-cipher-list {
            type tls-1_2-local-cipher-list-enum;
            default "ecdhe-rsa-with-aes-128-gcm-sha256";
            default "ecdhe-rsa-with-aes-256-gcm-sha384";
            default "ecdhe-ecdsa-with-aes-128-gcm-sha256";
            default "ecdhe-ecdsa-with-aes-256-gcm-sha384";
            description "Specifies the list of ciphers for TLS 1.2 based on
            ietf-tls-common. Due to TLS 1.2 being the minimum supported protocol
            version, some of the hereby listed ciphers can not be used.
            If a cipher excluded by RFC7540 is configured, alarm
            DIA Diameter Transport Vulnerability is raised for the related
            dtls-profile.
            Chosen ciphers must match the deployed certificate.
            Update Effect: All established Diameter Peer connections linked
            to related dtls-profile are dropped and reestablished with updated
            information.";
            reference "https://www.openssl.org/docs/man1.1.1/man1/ciphers.html,
              https://tools.ietf.org/html/rfc7540#appendix-A";
          }
          leaf security-level {
            type uint16 {
              range "3..5";
            }
            default 3;
            description "Specifies the TLS security level used with this
            profile.
            Hardening procedure can increase the applied security level.
            Level 3
            Security level set to 128 bits of security. As a result RSA, DSA and
            DH keys shorter than 3072 bits and ECC keys shorter than 256 bits
            are prohibited. In addition to the level 2 exclusions cipher suites
            not offering forward secrecy are prohibited. TLS versions below 1.1
            are not permitted. Session tickets are disabled.
            Level 4
            Security level set to 192 bits of security. As a result RSA, DSA and
            DH keys shorter than 7680 bits and ECC keys shorter than 384 bits
            are prohibited. Cipher suites using SHA1 for the MAC are prohibited.
            TLS versions below 1.2 are not permitted.
            Level 5
            Security level set to 256 bits of security. As a result RSA, DSA and
            DH keys shorter than 15360 bits and ECC keys shorter than 512 bits
            are prohibited.
            Update Effect: All established Diameter Peer connections linked
            to related dtls-profile are dropped and reestablished with
            updated information.";
            reference "https://www.openssl.org/docs/man1.1.1/man3/
              SSL_CTX_set_security_level.html";
          }
          leaf user-label {
            type string;
            description "Label for free use.";
          }
        }
        action list-attached-services {
          description "Used list the AAA Services exposing services through
          the own Diameter Node. Returns a structured list of AAA Services 
          exposing services through the own Diameter Node.";
          output {
            uses action-result;
            container structured-result {
              presence "Optional output";//needed for generated json maybevalue
              description "Optional JSON output returned by the diameter
              action.";
              leaf-list service-id {
                type string;
                description "Unique service identifier.";
              }
            }
          }
        }
        action list-peers {
          description "Used to list the Diameter Peers the related own Diameter
          Node is in relation with. The resulting Diameter Peer list is scoped
          in accordance with the command argument provided. Returns a structured
          list of Diameter Peers identified by related Origin-Host.";
          input {
            uses peer-properties;
            leaf host-filter {
              type string;
              default ".*";
              description "Used to express a filter over the Origin-Host of
              the Diameter Peer. By default all hosts are listed.
              It should be expressed as a regular expression 
              (eg: node1\\.operator1\\.com, .*\\.operator1\\.com). The provided
              regular expression will be used to search for Diameter Peers,
              with matching Origin-Host, connected to the own Diameter Nodes.";
            }
          }
          output {
            uses peer-list-information;
          }
        }
        action show-peer {
          description "Used to provide available information about the
          indicated Diameter Peer. The specified peer-origin-host should
          refer to a Diameter Node which is a peer of the own Diameter Node.
          Dumps structured information about the indicated Diameter Peer.";
          input {
            leaf peer-origin-host {
              type inet:domain-name;
              mandatory true;
              description "Used to set the peer OriginHost information. Should
              refer to the Diameter Peer of the own Diameter Node";
            }
          }
          output {
            uses peer-information;
          }
        }
        action list-connections {
          description "Used to list the Peer connections of the indicated
          Diameter Peer. Dumps structured information about the peer
          connections of indicated Diameter Peer. The specified peer-origin-host
          should refer to a Diameter Node which is a peer of the own
          Diameter Node";
          input {
            leaf peer-origin-host {
              type inet:domain-name;
              mandatory true;
              description "Holds the Origin-Host of the Diameter Peers
              connection information should be exposed about. Typically, one of
              the Peers listed with list-peers action.";
            }
          }
          output {
            uses connection-list-information;
          }
        }
        action show-connection {
          description "Used to provide information about the indicated diameter
            Peer connection. The ought Diameter Peer connection must be
            identified by a connection-id (as returned by the list-connections
            action). Dumps structured information about the indicated Diameter
            Peer connection.";
          input {
            leaf connection-id {
              type string;
              mandatory true;
              description "Used to indicate the identity of the relevant
              Diameter Peer connection.";
            }
          }
          output {
            uses connection-information;
          }
        }
        action kill-connection {
          description "Used to kill the established diameter connection
          identified by connection-id. 
          This asynchronous action is mainly created for
          troubleshooting purposes. One can kill a connection to:
          Test Diameter Service link fail-over and link reestablishment
          capabilities.
          Enforce diameter link reestablishment towards another Diameter
          Service Instance in connection termination mode.
          The kill-connection action will not disable a diameter peer
          connection. That is, a killed connection might be setup again
          by any of the related nodes (own Node or Peer).
          Operation success should be checked by using the list-connections
          action. One should check uptime to realize how recent a peer
          connection is.";
          input {
            leaf connection-id {
              type string;
              mandatory true;
              description "Used to indicate the identity of the connection
              to be killed. The identity of a connection towards a Peer can be
                obtained with show-peer action performed for relevant peer.";
            }
          }
          output {
            uses action-result;
          }
        }
        action kill-all-connections-of-peer {
          description "Used to kill all the established diameter connections
          towards the indicated Peer.
          This asynchronous action is mainly created for troubleshooting
          purposes:
          One can kill connections and test system link failover and link
          re-establishment capabilities.
          By need enforcing diameter link re-establishment through another
          PL node of local Diameter Node can be obtained this ways as
          well in connection termination mode.
          A kill operation is not a disable operation. That is, a killed
          connection might be setup again by any of the related nodes
          (own Node or Peer). Operation success should be checked using
          action list-connections. After killing a connection yet another
          one can be initiated either by local node or Peer. One
          should check uptime to realize how recent a Peer connection is.";
          input {
            leaf peer-origin-host {
              type inet:domain-name;
              mandatory true;
              description "Used to indicate the peer OriginHost towards
              which established connections should be killed.";
            }
          }
          output {
            uses action-result;
          }
        }
        action kill-all-connections {
          description "Used to kill all the Diameter Peer connections of the
            Diameter Node. This asynchronous action is mainly created for
            troubleshooting purposes:
            One can kill connections and test system link failover and link
            re-establishment capabilities.
            By need enforcing diameter link re-establishment through another
            PL node of local Diameter Node can be obtained this ways as
            well in connection termination mode.
            Operation success should be checked using action
            list-connections. After killing a connection yet another one
            can be initiated either by own Node or Peer. One should
            check uptime to realize how recent a Peer connection is.";
          output {
            uses action-result;
          }
        }
        action show-deployed-certificates {
          description "Prints structured information about the certificates,
            keys and trusts that have been defined by the Diameter helm.
            Note, certs must be defined for TLS by the Diameter deployment in
            advance.
            Only these pre-defined certs can be set for the related
            leafrefs of a tls-profile and dtls-profile on the NBI.
            Referred certs must have already been enrolled to ietf-keystore
            and ietf-truststore.";
          output {
            leaf success {
              type boolean;
              mandatory true;
              description "Shows if action was successful.";
            }
            leaf result {
              type string;
              description "Contains ids of deployed certs,keys and trusts.";
            }
          }
        }
      }
      /*********************************************************************/
      list host-address-resolver {
        key "id";
        description "A host-address-resolver is used to resolve or determine
        a host-local IP address the Local Endpoints shall use during peer
        connection establishment. This object can be used when the
        Diameter Service is deployed on a target system where a Diameter node
        (a POD hosting a Diameter Service instance) might be associated with
        more than one IP address (see also Kubernetes Cluster Networking).
        Changes on host-address-resolver level are influencing all
        established Peer connections using the related IP address. That
        is, affected Peer connections are closed then reestablished by
        need using updated information.";
        leaf id {
          type string;
          description "Used to specify the key of the host-address-resolver
          instance.";
        }
        leaf user-label {
          type string;
          description "Label for free use.";
        }
        leaf ip-family {
          type enumeration {
            enum ipv4 {
              value 0;
              description "IP family is restricted to IPv4.";
            }
            enum ipv6 {
              value 1;
              description "IP family is restricted to IPv6.";
            }
            enum any {
              value 2;
              description "IP family of the primary IP address specified on
              kubernetes level is used.";
            }
          }
          default "any";
          description "When dual-stack feature is enabled on Kubernetes level,
          ip-family can be used to specify the IP family of the address resolved
          by the host-address-resolver. In other words, to specify the IP family
          of the IP address the related Diameter EP should bind to.
          In case the host-address-resolver is configured with an ip-family for
          which there is no IP address allocated to the Diameter Service in the
          Kubernetes cluster, alarm DIA Diameter Configuration Incomplete is
          raised";
        }
        leaf linux-env-var {
          type string;
          mandatory true;
          description "Used to specify a Linux environment variable name
          the Diameter Service instances must use to resolve the related 
          local IP address they should bind to.
          The Linux environment variable specified must be injected in
          related Diameter Service containers as well. Note, Diameter Service
          injects POD_IP and POD_IPS to represent Kubernetes runtime attributes
          .status.podIP and .status.podIPs. The .status.podIPs value holds the
          addresses allocated to the POD. The order in which the IPv4 and IPv6
          address are placed in the .status.podIPs depends on the configuration
          of the Kubernetes cluster. The first item in .status.podIPs is
          matching the legacy .status.podIP content.
          Update Effect: All established Diameter Peer connections linked
          to Local Endpoints referring to the host-address-resolver are
          dropped and reestablished using the updated information.";
        }
      }
      /*********************************************************************/
      list secondary-network-address {
        key "id";
        status current {
          yexte:preliminary;
          yexte:status-information "Under development for SCTP MH, SENP support.
          Function has not been verified by user applications, yet.";
        }
        description "A secondary-network-address instance is used to specify
        addressing information used by SENP nVIP microservice in order to
        uphold separation from the traffic distributed on the default primary
        network within the Kubernetes cluster.";
        leaf id {
          type string;
          description "Used to specify the key of the secondary-network-address
          instance.";
        }
        leaf senp-nvip-address {
          type inet:ip-address;
          description "Used to specify the VIP address provided by SENP nVIP.
          Update Effect: All established Diameter Peer connections linked
          to related SENP VIP address are dropped and reestablished with
          updated information.";
        }
        leaf senp-nvip-sctp-service-path {
          type string;
          description "Used to specify the secondary networking service path
          that together with related VIP address defines the SENP properties
          for the diameter SCTP traffic.
          Update Effect: All established SCTP Diameter Peer connections linked
          to related SENP address are dropped and reestablished with updated
          information.";
        }
        leaf user-label {
          type string;
          description "Label for free use.";
        }
      }
      /*********************************************************************/
      list local-endpoint {
       must '( enabled = "false" ) or'
       + '(initiate-connection-to-peer and not(terminate-connection-from-peer)'
       + 'and not(terminate-connection-from-accepted-peers)) or'
       + '(not(initiate-connection-to-peer) and (terminate-connection-from-peer'
       + ' or terminate-connection-from-accepted-peers))' {
          error-message 'An enabled transport must either be configured as a 
          client or as a server. '
          + 'Either set initiate-connection-to-peer or '
          + 'terminate-connection-from-peer or '
          + 'terminate-connection-from-accepted-peers';
          error-app-tag "local-endpoint-client-or-server";
        }
        must '( enabled = "false" ) or'
           + '( transport-sctp or transport-tcp )' {
          error-message "At least one transport must be configured for an
          enabled local-endpoint.";
          error-app-tag "local-endpoint-transport";
        }
        must '( enabled = "false" ) or '
        + '(not (initiate-connection-to-peer)) or (count('
        + '/diameter/peer-table/static-peer[id=current()/'
        + 'initiate-connection-to-peer][enabled="true"]'
        + '/remote-endpoint[enabled="true"]'
        + ') != 0)' {
          error-message "It is mandatory to define at least a remote endpoint if
          the own Diameter Node is having an enabled local-endpoint configured
          to initiate connections towards the related Diameter Peer.";
          error-app-tag "initiate-connection-to-peer-remote-endpoint";
        }
        key "id";
        description "A local-endpoint instance is used to specify a Local
        Endpoint for the own Diameter Node.
        A Local Endpoint can play one of the following roles:
        Connection Initiation
        The Local Endpoint is configured to play a transport connection
        initiation role towards the configured Diameter Peer. That is,
        the Local Endpoint is playing a client role in the Peer connection
        setup flow.
        When initiating connections towards a Diameter Peer the
        initiate-connection-to-peer of the local-endpoint should
        hold an object reference pointing to that Diameter Peer
        (represented by a static-peer together with related remote-endpoint)
        towards which the connection initiation and related peer
        connection establishment is to be performed.
        If the local-endpoint is configured as client, it is possible to define
        both TCP and SCTP transports (see transport-tcp and transport-sctp) at
        the same time. This kind of setup could be used to implement a fallback
        from one transport protocol to the other (see also rank parameter of
        the local-endpoint), as only one of the transports (one connection per
        computing resource) will be set-up by the stack. The one having the
        lowest rank is tried first, if it fails, the next configured transport
        connection is tried.
        Connection Termination
        The Local Endpoint is configured to play a connection termination
        role for Peer Diameter Nodes. That is, the related Local Endpoint is
        playing a server role in the Peer connection setup flow. It listens
        on the configured address and port pairs and accepts incoming
        transport connection requests initiated by Peer Diameter Nodes.
        The collection of Peer Diameter Nodes allowed to setup peer
        connections towards a Local Endpoint of the own Diameter Node can
        be constrained by either using the generic Peer filtering
        capabilities provided by the dynamic-peer-acceptor or by using
        concrete Peer specification capabilities provided by the
        static-peer or both.
        The Diameter Peer initiated connection acceptance constraints are
        expressed for a local-endpoint by loading the related
        terminate-connection-from-peers and/or
        terminate-connection-from-accepted-peers with an object reference
        pointing to those static-peer and respectively dynamic-peer-acceptor
        instances that are used to express the different connection acceptance
        conditions.
        If local-endpoint is configured as a server, there must be only one
        transport defined for it, either SCTP or TCP (see transport-tcp and
        transport-sctp). If both transports are required for the server, two
        local-endpoint instances are needed.
        A Local Endpoint can either play a connection initiation (client)
        role or connection termination (server) role, therefore, a Local
        Endpoint must either have the terminate-connection-from-* reference
        or the initiate-connection-to-peer reference filled with a valid
        reference value but never both of them.
        In opposite to SCTP, TCP can only handle one address for a transport
        connection. As a result, in case of transport-tcp, when multiple IP
        addresses provided, one available address will be selected at random by
        the related endpoint during connection setup. If more TCP connections
        are required, more local-endpoints must be specified referring to
        multiple address instances.
        A Local Endpoint can be assigned with several transport
        capabilities. A transport capability represents a certain transport
        protocol implementation. The following transport capabilities
        (transport protocol implementations) are supported by the Diameter
        Service:
        TCP
        Linux Kernel implementation of the Transmission Control Protocol
        (TCP).
        E-SCTP
        Proprietary user-space implementation of the Stream Control
        Transmission Protocol (SCTP).
        A Local Endpoint in client role can be assigned with up to two
        transport capabilities representing distinct transport protocol
        implementations. That is, for instance, one of the transport
        capability can represent a TCP protocol implementation while the
        other one an SCTP protocol implementation.
        That transport capability is selected first for Peer connection
        handling which presents the highest configured rank and it is
        potentially valid for connection establishment (for instance,
        the configured address is available on the target system). Upon
        multiple valid transport capabilities with same rank one of them
        is selected in a random way (for example when specifying one TCP
        and one SCTP transport capability using same rank).
        A AAA Service can have assigned any number of Local Endpoints
        with different roles and transport capabilities.
        The Diameter Service runs in a cluster configuration on the target
        system. That is, it might span on an arbitrary number of compute
        resources (nodes, interpreted as POD individuals for ADP).
        A Local Endpoint can be configured to start in single or multiple
        instances on cluster level. The number of instances started for
        a Local Endpoint can be configured to arbitrary value but the
        actual instances started will never pass the number of compute
        resources the Diameter Service is instantiated on.
        In case no host-address-resolver is referred by a local-endpoint,
        and secondary networking is not specified during installation, the
        primary IP address on Kubernetes configuration level (variable POD_IP
        hosting the value of Kubernetes runtime attribute .status.podIP)
        returned by the inbuilt default host resolver is used for TCP
        transport. For SCTP transport the default E-SCTP behavior is to use
        all local addresses available on primary network, independently from
        the referred host-address-resolver existence.
        When secondary networking is defined by the installation, and no
        secondary-network-address is assigned, the default SENP VIP(s) and
        service path defined by the installation is used for diameter traffic.
        Changes on local-endpoint are applied immediately on Diameter
        Service level. The majority of value changes on a local-endpoint will
        have as result the drop of related Peer connections and reestablishment
        by need with updated information. Diameter Service level queued
        egress request messages will be resent to realted Diameter Peers.";
        leaf id {
          type string;
          description "Used to specify the key of the local-endpoint
          instance.";
        }
        leaf enabled {
          type boolean;
          default "true";
          description "Used to enable or disable the use Local Endpoint.
          When disabled, the following alarm is raised:
          ADP Diameter Managed Object Disabled
          Update Effect: All established Diameter Peer connections related
          to the Local Endpoint are closed if value is set to false.";
        }
        leaf dscp {
          type inet:dscp;
          default "0";
          description "Used to specify the Differentiated Service Code Point
          (DSCP) to be used during Peer connection setups for the 
          Local Endpoint.
          Update Effect: Depends on used transport capability.
          In case of TCP there is no impact on affected peer
          connections. The DSCP of affected Peer connections are updated
          without impact on traffic and related connections.
          In case of SCTP the affected Peer connections are dropped and
          reestablished by need with updated transport properties.";
        }
        leaf instance-count {
          type uint32 {
            range "0..255";
          }
          default "1";
          description "Used to specify the number of instances a Local Endpoint
          configured with connection initiation (client) role shall
          have. This has no effect on Local Endpoint configured with
          connection termination (server) role.
          It can take a value from one of the following ranges:
          0: The Local Endpoint configured in connection initiation
          (client) mode shall have an instance started for each of the
          Diameter Service instances. That is, the actual Local Endpoint
          instance number is dynamically changing in accordance with actual
          Diameter Service cluster size. More Local Endpoint instances are
          created when the Diameter Service is scaled-out and Local Endpoint
          instances are removed when the Diameter Service is scaled-in.
          1..255: The Local Endpoint configured in connection initiation
          (client) mode shall not pass on cluster level the indicated
          number of instances (a value specified between 1 and 255). The
          actual number of Local Endpoint instances created by Diameter
          Service will never be higher than the lowest threshold value
          represented by either of the actual Diameter Service cluster
          size or the configured Local Endpoint instance-count.
          The default value is 1. That is, a single instance is created
          for a Local Endpoint configured in connection initiation mode.
          The default setting assures standards behavior in relation with
          the restriction on number of Peer connections to be set towards
          same diameter peer.
          To have an effect when setting a value higher than one for
          instance-count, restrict-connections of the referred
          static-peer or dynamic-peer-acceptor must be set to false
          (see static-peer, dynamic-peer-acceptor).
          Update Effect: Depends on local endpoint connection role.
          In case of connection initiation (client) role, the configured
          amount of Local Endpoint instances will be applied. New Local
          Endpoint instances are added by need without affecting existing
          ones. Existing Local Endpoint instances with related peer
          connections are removed by need without affecting the other ones.
          In case of connection termination (server) role, there is no
          effect on value change.";
        }
        leaf watchdog-timer {
          type uint32 {
            range "6000..4294967295";
          }
          units "milliseconds";
          default "30000";
          description "Used to configure the Watchdog Initial Timer (Twinit)
          of the Peer connections assigned with the local endpoint (see also
          Authentication, Authorization and Accounting (AAA) Transport
          Profile (RFC 3539) IETF: STANDARD).
          Unit: millisecond (ms)
          Update Effect: No impact on affected Peer connections.";
        }
        leaf reconnect-timer {
          type uint32 {
            range "1000..4294967295";
          }
          units "milliseconds";
          default "30000";
          description "Used to configure the Tc timer
          (https://tools.ietf.org/html/rfc6733#section-12) of the peer
          connections assigned with the local endpoint. That is, it is used
          to set the frequency the transport connection attempts are done
          to a diameter peer with whom no active transport connection exists.
          It is not recommended to configure too small Tc timer, as it can
          result in transport failures if related NAT cache is not flushed
          before the retry.
          Unit: millisecond (ms)
          Update Effect: No impact on affected Peer connections.";
        }
        leaf node {
          type leafref {
            path "/diameter/transport/node/id";
          }
          mandatory true;
          description "Used to assign a Local Endpoint with an own Diameter
          Node represented by related node instance.
          Should take as single value a reference to that node to which
          the Local Endpoint must be assigned (see node).
          Update Effect: All established Diameter Peer connections assigned
          to local endpoint are dropped and reestablished with updated
          own Diameter Node information.";
        }
        leaf initiate-connection-to-peer {
          type leafref {
            path "/diameter/peer-table/static-peer/id";
          }
          description "Used to set a Local Endpoint to play a connection
          initiator (client) role.
          It can take a value if terminate-connection-from-accepted-peers
          and terminate-connection-from-peer are not set.
          It shall refer to that static-peer that represents the Diameter Peer
          the Local Endpoint should initiate connection establishment towards
          (see static-peer).
          Update Effect: All established Diameter Peer connections assigned
          to local endpoint are dropped and reestablished by need with
          updated information.";
        }
        leaf disconnect-cause-handling-policy {
          type leafref {
            path "/diameter/policies/disconnect-cause-handling-policy/id";
          }
          description "Used to express the Disconnect-Cause handling policy
          to follow upon Peer connection close as result of operations over
          service instances or upon AAA Service disconnection from Diameter
          Service.
          Should take as value a reference to disconnect-cause-handling-policy.
          Update Effect: No impact on established Peer connections. Upon
          update, the Local Endpoint will apply the referred policy.
          If not set the Diameter Service uses the default Disconnect-Cause
          handling policy set to REBOOTING.";
        }
        leaf-list terminate-connection-from-peer {
          type leafref {
            path "/diameter/peer-table/static-peer/id";
          }
          description "Used to set a Local Endpoint to play connection
          termination (server) role.
          It can take a value if the initiate-connection-to-peer is not set.
          It shall hold a list of references towards those static-peer
          instances which are representing Diameter Peers allowed to
          initiate connection establishment towards the Local Endpoint
          (see static-peer).
          Update Effect: All established Diameter Peer connections assigned
          to local endpoint are dropped and reestablished by need with
          updated information.";
        }
        leaf-list terminate-connection-from-accepted-peers {
          type leafref {
            path "/diameter/peer-table/dynamic-peer-acceptor/id";
          }
          description "Used to set a Local Endpoint to play connection
          termination (server) role.
          It can take a value if the initiate-connection-to-peer is not set.
          It shall hold a list of references towards those dynamic-peer-acceptor
          instances which are used to express a pattern based representation of
          Diameter Peers allowed to initiate connection establishment
          towards the Local Endpoint (see dynamic-peer-acceptor).
          Update Effect: All established Diameter Peer connections assigned
          to local endpoint are dropped and reestablished by need with
          updated information.";
        }
        leaf user-label {
          type string;
          description "Label for free use.";
        }
        /*********************************************************************/
        container transport-tcp {
          presence "TCP transport is in use";
          description "Used to assign TCP transport capability for a Local
          Endpoint.";
          leaf port {
            type inet:port-number;
            must '(. != 0 and not(../../initiate-connection-to-peer) ) or '
               + '(. = 0 and ../../initiate-connection-to-peer )' {
              error-message "Client must keep port on zero, "
                          + "server must set a non-zero port";
              error-app-tag "local-tcp-endpoint-port";
            }
            default "0";
            description "Used to specify the port to be used by the TCP
            transport capability of a Local Endpoint.
            Update Effect: All established Diameter Peer connections
            assigned to local endpoint are dropped and reestablished with
            updated information.
            Depending on local endpoint role, it defaults to:
            0: if local endpoint is configured in connection initiation
            (client) mode.
            3868: if local endpoint is configured in connection termination
            (server) mode.";
          }
          leaf rank {
            type uint32;
            description "Used to express precedence for transport capability
            selection for a Local Endpoint.
            That transport capability will be selected for a Local
            Endpoint that is valid to use (for instance, diameter can
            bind to specified address) and contains the lowest rank. In
            case of multiple valid transport capabilities assigned to a
            Local Endpoint with same rank one will be selected by random.
            Update Effect: No effect on already established Peer connections
            for related Local Endpoint. The new value is considered for
            newly established Peer connections.";
          }
          leaf backlog {
            type uint32;
            default "1024";
            description "Used to specify the backlog size of incoming
            connections handled by a Local Endpoint (the queue size of sockets
            in LISTEN state, see 
            http://man7.org/linux/man-pages/man2/listen.2.html).
            This is only valid for Local Endpoints configured in connection
            termination (server) role.
            The value applied also depends on underlying OS settings
            (might be constrained by OS to less than configured).
            Update Effect: All established Diameter Peer connections
            assigned to local endpoint are dropped and reestablished with
            updated information.";
          }
          leaf no-delay {
            type boolean;
            default "true";
            description "Used to enable or disable the use of the Nagle
            algorithm for the TCP transport capability of a Local Endpoint.
            By default, TCP_NODELAY socket option is
            applied, the use of Nagle algorithm (see
            https://tools.ietf.org/html/rfc3539#section-3.2) is disabled.
            Update Effect: All established Diameter Peer connections
            assigned to local endpoint are preserved and updated with
            new configuration.";
          }
          leaf-list address {
            type leafref {
              path "../../../host-address-resolver/id";
            }
            description "Offers the possibility to assign an IP address to
            a transport capability. In case of multiple IP addresses provided,
            one available address will be selected at random by the related
            endpoint during connection setup.
            Update Effect: All established Diameter Peer connections
            for the transport capability assigned to local endpoint are
            dropped and reestablished by need with updated information.";
          }
          leaf tls-profile {
            if-feature "ks:keystore-supported and ts:truststore-supported";
            type leafref {
              path "/diameter/transport/node/tls-profile/id";
            }
            description "If defined, endpoint uses TLS to secure the
            communication with properties of the referred tls-profile.
            If not defined, alarm DIA Diameter Transport Vulnerability is raised
            for the related endpoint.
            Update Effect: All established Diameter Peer connections assigned
            to local tcp endpoint are dropped and reestablished with updated
            information.";
          }
          leaf tls-host-name-validation {
            //when "../tls-profile"; json generation skips it
            if-feature "ks:keystore-supported and ts:truststore-supported";
            type boolean;
            default "true";
            description "Can be used to turn off hostname validation on TLS
            secured static connections. By default, peer certificate received
            during TLS handshake must contain the id defined by peer-origin-host
            of referred static-peer instance.
            If turned off, alarm DIA Diameter Transport Vulnerability is raised
            for the related endpoint.
            Note, there is no hostname validation for dynamic Peers allowed by
            filters in dynamic-peer-acceptor instances.
            Has no effect on connections without TLS, that is if tls-profile is
            empty.
            Update Effect: All established Diameter Peer connections assigned
            to local tcp endpoint are dropped and reestablished with updated
            information.";
            reference "https://www.openssl.org/docs/man1.1.1/man3/
            X509_check_host.html";
          }
        }
        /*********************************************************************/
        container transport-sctp {
          presence "SCTP transport is in use";
          description "Used to assign SCTP transport capability for a Local
          Endpoint. Either primary or secondary NW address(es) or no
          address is to be defined.";
          leaf port {
            type inet:port-number;
            must '(. != 0 and not(../../initiate-connection-to-peer) ) or '
               + '(. = 0 and ../../initiate-connection-to-peer )' {
              error-message "Client must keep port on zero, "
                          + "server must set a non-zero port";
              error-app-tag "local-sctpe-endpoint-port";
            }
            default "0";
            description "Used to specify the port to be used by the E-SCTP
            transport capability of a Local Endpoint.
            Update Effect: All established Diameter Peer connections
            assigned to local endpoint are dropped and reestablished with
            updated information.
            Depending on local endpoint role, it defaults to:
            0: if local endpoint is configured in connection initiation
            (client) mode.
            3868: if local endpoint is configured in connection termination
            (server) mode.";
          }
          leaf rank {
            type uint32;
            description "Used to express precedence for transport capability
            selection for a Local Endpoint.
            That transport capability will be selected for a Local
            Endpoint that is valid to use (for instance, diameter can
            bind to specified address) and contains the lowest rank. In
            case of multiple valid transport capabilities assigned to a
            Local Endpoint with same rank one will be selected by random.
            Update Effect: No effect on already established Peer connections
            for related Local Endpoint. The new value is considered for
            newly established Peer connections.";
          }
          leaf outbound-streams {
            type uint16;
            units "number of streams";
            default "1";
            description "Used to configure the Number of Outbound Streams (OS)
            (https://tools.ietf.org/html/rfc4960#section-3.3.2) wished
            for the associations created for the Peer connections assigned
            with the local endpoint (see also Stream Control Transmission
            Protocol (RFC 4960) IETF: STANDARD).
            Update Effect: All established Diameter Peer connections
            assigned to local endpoint are dropped and reestablished with
            updated information.
            Unit: Count";
          }
          leaf max-inbound-streams {
            type uint16;
            units "number of streams";
            default "1";
            description "Used to configure the Number of Inbound Streams (MIS)
            (https://tools.ietf.org/html/rfc4960#section-3.3.2) wished
            for the associations created for the Peer connections assigned
            with the local endpoint (see also Stream Control Transmission
            Protocol (RFC 4960) IETF: STANDARD).
            Update Effect: All established Diameter Peer connections
            assigned to local endpoint are dropped and reestablished with
            updated information.
            Unit: Count";
          }
          leaf-list address {
            type leafref {
              path "../../../host-address-resolver/id";
            }
            description "Not used. Gives the possibility to assign IP
            address(es) to an E-SCTP transport capability. Note, Diameter
            does not pass it to E-SCTP to trigger default E-SCTP behaviour
            that is binding to all available local addresses.
            Update Effect: All established Diameter Peer connections
            for the transport capability assigned to local endpoint are
            dropped and reestablished by need with updated information.";
          }
          leaf-list secondary-network-address {
            type leafref {
              path "../../../secondary-network-address/id";
            }
            description "Gives the possibility to assign a SENP VIP address
            and related service path to an E-SCTP transport capability. At
            least two addresses are required for SCTP Multi-homing.
            Diameter passes the configured values to E-SCTP.
            Update Effect: All established Diameter Peer connections
            for the transport capability assigned to local endpoint are
            dropped and reestablished by need with updated information.";
          }

          leaf dtls-profile {
            if-feature "ks:keystore-supported and ts:truststore-supported";
            type leafref {
              path "/diameter/transport/node/dtls-profile/id";
            }
            description "If defined, SCTP service uses DTLS to secure the
            communication with properties of the hereby referred dtls-profile.
            If not defined, alarm DIA Diameter Transport Vulnerability is raised
            for the related endpoint.
            Update Effect: All established Diameter Peer connections assigned
            to local sctp endpoint are dropped and reestablished with updated
            information.";
          }
          leaf tls-host-name-validation {
            //when "../tls-profile"; json generation skips it
            if-feature "ks:keystore-supported and ts:truststore-supported";
            type boolean;
            default "true";
            description "Can be used to turn off hostname validation on DTLS
            secured static connections. By default, peer certificate received
            during TLS handshake must contain the id defined by peer-origin-host
            of referred static-peer instance.
            If turned off, alarm DIA Diameter Transport Vulnerability is raised
            for the related endpoint.
            Note, there is no hostname validation for dynamic Peers allowed by
            filters in dynamic-peer-acceptor instances.
            Has no effect on connections without DTLS, that is if dtls-profile
            is empty.
            Update Effect: All established Diameter Peer connections assigned
            to local tcp endpoint are dropped and reestablished with updated
            information.";
            reference "https://www.openssl.org/docs/man1.1.1/man3/
            X509_check_host.html";
          }
          leaf sctp-profile {
            type leafref {
              path "/sctpadp:sctp/sctpadp:sctp-profile/sctpadp:id";
            }
            description "If defined, SCTP endpoint uses configuration from
            the referred SCTP profile. Otherwise, default sctp configuration is
            used (profile 0).
            Update Effect: All established Diameter Peer connections assigned
            to local sctp endpoint are dropped and reestablished with updated
            information.";
          }
        }
      }
      action dump-transport-data {
        description "Perform a transport dump. For more information refer
        to transport dump interface.";
        output {
          uses transport-information;
        }
      }
    }
    /*********************************************************************/
    list peer-selector {
      key "id";
      description "A peer-selector instance is used to group a collection
      of Diameter Nodes to form a destination domain egress request messages
      can be passed towards as result of evaluation of those routing entries
      that are referring to it.
      Practically, in routing perspective, a peer-selector instance returns
      a set of Diameter Peer connections organized in increased order of
      their determined rank. That available Diameter Peer connection will
      be selected when matching criteria is found during related routing
      entry evaluation that is with the lowest rank.
      Egress request routing selects a connection from this returned set of
      connections by using a Session-Id AVP based hashing algorithm. If the
      Session-Id AVP is not present in the related diameter request message
      connection is selected in random order.
      In case multiple Peers referred by the selector through static-peer-group,
      peer-reference or dynamic-peer-group have equal ranks, then all the
      connections to these Peers are returned by the selector.
      If the ranks are different, only the Peer or Peers with the lowest rank is
      selected.
      The peer selections (or peer groups) should be used when Diameter
      Peers are to be grouped based on different criteria to form
      destination domains egress request messages can be passed towards as
      result of related routing entry evaluation. That is, peer selections
      are to be created only with the purpose to use them as destination
      domains during routing entry evaluations.
      In other cases the use of peer selections (peer groups) can be
      omitted. Define peer selections only if the route-to-peer-selection
      action is planned to be used when creating routing rules.";
      leaf id {
        type string;
        description "Used to specify the key of the peer-selector instance.";
      }
      leaf update-message-destination {
        type boolean;
        default "false";
        status current {
          yexte:preliminary;
          yexte:status-information "Under development. Function has not been
          verified by user applications, yet.";
        }
        description "When set to true in linux service-execution-environment,
        Diameter routing function executing route-to-peer-selection routing
        action checks if the Destination-Host and Destination-Realm AVPs are
        included in the egress request message. If they are included, Diameter
        ensures that they do match the peer-origin-host of the selected
        static-peer and its realm, respectively.
        This function is to be used by diameter user applications utilizing
        peer-selector to implement fail-over between multiple directly
        connected Peer Nodes (probably serving different realms) while
        Destination-Host and Destination-Realm AVP pair is included into the
        request by the user application. Message destination updates performed
        by Diameter routing ensures that the request won't get rejected by the
        message destination validation even at alternative Diameter Peer
        Nodes.";
      }
      leaf user-label {
        type string;
        description "Label for free use.";
      }
      /*********************************************************************/
      list static-peer-group {
        key "id";
        description "A static-peer-group instance is used to specify a group
        of Diameter Peers by referring to their explicit representation
        expressed through related static-peer instances.
        Any change in the number of static peers assigned to the
        static-peer-group instance will be applied immediately impacting in this
        way the related routing entries evaluated by the routing logic of
        diameter.";
        leaf id {
          type string;
          description "Used to specify the key of the static-peer-group
          instance.";
        }
        leaf rank {
          type uint32;
          default "0";
          description "Used to assign a rank to the group of Diameter
          Peers represented by the collection of static-peer instances
          referred by child peer-reference instances.
          The lower the rank value the higher the configured rank of the
          static-peer-group. The default value is 0 (highest rank).
          Update Effect: No effect on already established Peer connections
          but on routing information. Introduced change will be applied
          next time a routing entry is evaluated.";
        }
        leaf update-message-destination {
          type boolean;
          default "false";
          status deprecated {
            yexte:status-information "Preliminary version has been withdrawn,
            replaced by function on peer-selector level.";
          }
          description "Deprecated, use function on peer-selector level.";
        }
        leaf user-label {
          type string;
          description "Label for free use.";
        }
        /********************************************************************/
        list peer-reference {
          key "id";
          min-elements 1;
          description "A peer-reference instance is used to assign a rank
          to an explicit representation of a Diameter Peer (represented
          through referred static-peer instance).
          Any change on peer-reference instance values will be applied
          immediately impacting in this way the related routing entries
          evaluated by the routing logic of diameter.";
          leaf id {
            type string;
            description "Used to specify the key of the peer-reference
            instance.";
          }
          leaf rank {
            type uint32;
            default "0";
            description "Used to assign a rank to the set of Diameter
            Peers represented by the collection of static-peer instances
            referred by the peer values.
            The lower the rank value the higher the configured rank of
            the referred Peer Diameters. The default value is 0
            (highest rank).
            Update Effect: No effect on already established Peer connections
            but on routing information. Introduced change will be applied
            next time a routing entry is evaluated.";
          }
          leaf-list peer {
            type leafref {
              path "/diameter/peer-table/static-peer/id";
            }
            min-elements 1;
            description "Used to refer to a set of Diameter Peers,
            represented by related static-peer instances, ought to be assigned
            with same rank.
            Update Effect: No effect on already established Peer connections
            but on routing information. Introduced change will be applied
            next time a routing entry is evaluated.";
          }
          leaf user-label {
            type string;
            description "Label for free use.";
          }
        }
      }
      /*********************************************************************/
      list dynamic-peer-group {
        key "id";
        description "A dynamic-peer-group instance is used to specify a group of
        Diameter Peers by referring to their pattern based representation
        expressed through related dynamic-peer-acceptor instances.
        Any change in the number of Diameter Peers assigned dynamically
        (pattern based) to the dynamic-peer-group instance will be applied
        immediately impacting in this way the related routing entries
        evaluated by the routing logic of diameter.";
        leaf id {
          type string;
          description "Used to specify the key of the dynamic-peer-group
          instance.";
        }
        leaf rank {
          type uint32;
          default "0";
          description "Used to assign a rank to the set of Diameter Peers
          matching with related identity patterns expressed through
          dynamic-peer-acceptor instances referred by the peer values.
          The lower the rank value the higher the configured
          rank of the referred Diameter Peers. The default value is 0
          (highest rank).
          Update Effect: No effect on already established Peer connections
          but on routing information. Introduced change will be applied
          next time a routing entry is evaluated.";
        }
        leaf-list peer {
          type leafref {
            path "/diameter/peer-table/dynamic-peer-acceptor/id";
          }
          min-elements 1;
          description "Used to refer to a set of dynamic-peer-acceptor
          instance accepted Diameter Peer ought to be assigned with same
          rank.
          Update Effect: No effect on already established Peer connections
          but on routing information. Introduced change will be applied
          next time a routing entry is evaluated.";
        }
        leaf user-label {
          type string;
          description "Label for free use.";
        }
      }
    }
    /*********************************************************************/
    list routing-table {
      key "id";
      description "Service diameter bases its message routing mechanism on
      the sequential evaluation of a collection of routing rules organized in a
      table called routing table.
      Each AAA Service using diameter must have a routing table
      associated. A routing table can be dedicated to a single AAA Service
      or shared between multiple AAA Services. There can be only a single
      routing table associated with a certain AAA Service.
      When a routing decision is to be made, the corresponding Diameter
      ingress or egress request message is checked against such a routing
      table by evaluating the routing rules (also called routing entries)
      in it one by one. The evaluation begins with the first routing rule
      in the relevant routing table then continues with the next ones up
      until either a routing rule fires or all the routing rules in the
      routing table are exhausted.
      A routing table is represented by a routing-table instance. Any
      change in the content of a routing table will be applied immediately
      impacting in this way the related routing rules/entries evaluated
      by the message routing mechanism of diameter.
      diameter will run a message routing mechanism whenever an ingress
      or egress request message is received by it:
      Egress Request Message Routing
      Whenever an egress request message is created by a AAA Service and
      passed down the diameter stack for delivery towards wanted destination
      a message routing mechanism is executed, on diameter stack level,
      to determine the Peer connection the egress request message is to be
      sent through in order to have the message starting its route towards
      its final destination. The message routing mechanism can either take
      direct instruction via the runtime API from a AAA Service on the
      Diameter Peer(s) to be used to send an egress request message
      towards, or it can determine it itself by using the information
      stored in a previously loaded routing table. That is, a routing
      table assigned to a AAA Service is evaluated during egress request
      message sending only if there is no peer list provided by related
      AAA Service during message sending request invocation method invoked
      to request sending an egress request message holds a peers=NULL list).
      Ingress Request Message Routing
      Whenever an ingress request message is received by the diameter
      stack through one of its Peer connections the AAA Service the
      message shall be passed towards is evaluated as well by using
      related routing entries expressed in the routing table.
      The Diameter answer messages always follow the routing path built
      for the related request message. This is the reason why answer
      messages are never matched against the routing rules defined in
      the routing table.
      The expression of a routing table for a AAA Service is mandatory. A
      routing table associated with a AAA Service is constructed by using
      one or several routing entries.";
      leaf id {
        type string;
        description "Used to specify the key of the routing-table instance.";
      }
      leaf-list service {
        type leafref {
          path "../../service/id";
        }
        min-elements 1;
        description "Used to refer to a set of AAA Services, represented
        by related service instances, the routing table should be associated
        with. A routing table can be assigned to many AAA Services. However,
        a AAA Service must be assigned with a single routing table only.
        Update Effect: No effect on already established Peer connections
        but on routing evaluation. Introduced change will be applied next
        time a routing entry is evaluated.";
      }
      leaf user-label {
        type string;
        description "Label for free use.";
      }
      /*********************************************************************/
      list routing-entry {
        key "id";
        min-elements 1;
        description "A routing-entry instance is used to specify a routing
        rule/entry. Each routing rule is constructed with the help of an
        expression and an action (see also related expression and action of the
        routing-entry instance).
        A routing rule can be enabled (default) or disabled by need. Only
        the enabled routing rules present in a routing table are considered
        during request message routing evaluation (disabled ones are just
        simply skipped).
        Any change in the content of a routing rule will be applied
        immediately impacting in this way the next routing rules/entries
        evaluated by the message routing mechanism of diameter.";
        leaf id {
          type uint32;
          description "Used to specify the key of the routing-entry instance.
          It shall be set to the number of the related routing rule/entry. This
          is how user can control the order of evaluation of a routing
          rule/entry in the related routing table.
          It is recommended to increment this value in steps of 100 or
          1000. In this way it is easy to inject further routing entries
          in an existing routing table between 2 existing routing entries.";
        }
        leaf enabled {
          type boolean;
          default "true";
          description "Used to enable or disable a routing rule/entry. When
          routing rule is disabled the routing rule is inactive, therefore,
          skipped by the diameter routing mechanism.
          When disabled, the following alarm is raised:
          ADP Diameter Managed Object Disabled
          Update Effect: No effect on already established Peer connections
          but on routing information. Introduced change will be applied
          next time a routing entry is evaluated.";
        }
        leaf expression {
          type string;
          mandatory true;
          description "Used to specify the expression part of a routing
          rule. The expression is that part of the routing rule the request
          message is matched against and evaluates to either TRUE or FALSE.
          If it evaluates to TRUE the action of the routing rule is
          executed.
          If it evaluates to FALSE the action of the routing rule is
          skipped and the routing mechanism continues with matching the
          request message against the expression of the next routing rule
          in the routing table.
          See more about routing language elements in Routing Rule Specification
          Language.
          Update Effect: No effect on already established Peer connections
          but on routing information. Introduced change will be applied
          next time a routing entry is evaluated.";
        }
        leaf action {
          type string;
          mandatory true;
          description "Used to specify the action part of a routing rule. The
          action is that part of the routing rule which is executed if the
          expression part of the routing rule evaluates to TRUE (that is, when
          the expression fires).
          See more about routing language elements in Routing Rule Specification
          Language.
          Update Effect: No effect on already established Peer connections
          but on routing information. Introduced change will be applied
          next time a routing entry is evaluated.";
        }
        leaf user-label {
          type string;
          description "Label for free use.";
        }
      }
      action dump-routing-table {
        description "Used to dump a textual, code-style representation of
        the routing table content.";
        output {
          uses action-result;
        }
      }
    }
    /*********************************************************************/
    container policies {
      description "Container holding various policy objects.";
      /*********************************************************************/
      list reroute-policy {
        must '( enabled = "false" ) or ( count( '
        + '/diameter/service[reroute-policy=current()/id][enabled="true"])!=0)'{
          error-message 'An enabled reroute-policy must be referred from at'
          + 'least one service';
          error-app-tag "reroute-policy-existence";
        }
        key "id";
        leaf id {
          type string;
          description "Key of the routing policy.";
        }
        leaf enabled {
          type boolean;
          default "true";
          description "Can be used to enable or disable the actual reroute
          policy.
          When disabled, the following alarm is raised:
          ADP Diameter Managed Object Disabled
          Update Effect: When enabled, the Diameter Service will apply
          the reroute-policy configuration.
          When disabled, the Diameter Service will apply the default
          behavior for egress request message rerouting.";
        }
        leaf-list reroute-error-id {
          type uint32 {
            range "1000..1999|3000..3999|4000..4999|5000..5999";
          }
          min-elements 1;
          description "Used to specify the Diameter Result Codes which
          should trigger an egress request message re-routing to alternate peer
          based on the configured routing table.
          Error codes are received in the Result-Code data field of a
          Result-Code AVP.
          The following error categories exists:
          1xxx (Informational)
          3xxx (Protocol Errors)
          4xxx (Transient Failures)
          5xxx (Permanent Failure)
          Update Effect: When set, the Diameter Service will start to
          behave according to the configured reroute-policy. It will
          automatically reroute messages upon reception of error answers
          holding the configured error codes.";
        }
        leaf user-label {
          type string;
          description "Label for free use.";
        }
        description "Specifies the answer message error codes for automatic
        message re-routing.
        The reroute-policy instance can be used to specify the answer
        message error codes triggering automatic egress request message
        rerouting using configured routing rules. The context of this
        policy can be scoped on AAA Service level.";
      }
      /*********************************************************************/
      list disconnect-cause-handling-policy {
        must '( enabled = "false" ) or (count('
        + '/diameter/transport/local-endpoint[disconnect-cause-handling-policy='
        + 'current()/id][enabled="true"] ) != 0 )' {
          error-message 'An enabled disconnect-cause-handling-policy must be'
          + 'referred from at least one local-endpoint';
          error-app-tag "disconnect-cause-handling-policy-existence";
        }
        key "id";
        description "Defines the content of the Disconnect-Cause AVP sent
        in the DPR.";
        leaf id {
          type string;
          description "Key of the disconnect cause handling policy.";
        }
        leaf enabled {
          type boolean;
          default "true";
          description "Can be used to enable or disable the actual
          DisconnectCause handling policy.
          When disabled, the following alarm is raised:
          ADP Diameter Managed Object Disabled
          Update Effect: When enabled, the Diameter Service will apply
          the disconnect-cause-handling-policy.
          When disabled, the Diameter Service will apply the default
          behavior for DPR message content construction.";
        }
        leaf disconnect-cause {
          type enumeration {
            enum rebooting {
              value 0;
              description "Disconnect-Cause AVP, REBOOTING.";
            }
            enum busy {
              value 1;
              description "Disconnect-Cause AVP, BUSY.";
            }
            enum do_not_want_to_talk_to_you {
              value 2;
              description "Disconnect-Cause AVP, DO_NOT_WANT_TO_TALK_TO_YOU.";
            }
          }
          default "rebooting";
          description "Defines the content of the Disconnect-Cause AVP to
          be sent in DPRs. 
          It is used in the Disconnect-Peer-Request message to inform the
          Diameter Peer about the reason of the disconnection.
          Update Effect: When set, the Diameter Service will apply the
          new configuration over scoped Local Endpoints. That is, upon
          Diameter Peer connection disconnection the configured error
          code will be applied.";
        }
        leaf user-label {
          type string;
          description "Label for free use.";
        }
      }
      /*********************************************************************/
      list congestion-handling-policy {
        must '( enabled = "false" ) or ( count( '
        + '/diameter/peer-table/static-peer[congestion-handling-policy'
        + '= current()/id][enabled = "true"] ) + '
        + ' count(
        /diameter/peer-table/dynamic-peer-acceptor[congestion-handling-policy'
        + ' = current()/id][enabled = "true"] ) != 0 ) ' {
          error-message 'An enabled congestion-handling-policy must be referred'
          + 'either from a dynamic-peer-acceptor or from a static-peer';
          error-app-tag "congestion-handling-policy-existence";
        }
        key "id";
        description "The congestion-handling-policy can be used to define
        the conditions (thresholds) which will trigger a traffic congestion
        handling towards relevant Diameter Peers. As result of congestion
        handling, congested Diameter Peer connection will be excluded
        temporarily from the list of potential routes and alternate routes
        (determined based on loaded routing table) will be used to send
        egress request messages towards relevant target Diameter Nodes.
        The context of this policy can be scoped on Peer level";
        leaf id {
          type string;
          description "Key of the congestion handling policy.";
        }
        leaf enabled {
          type boolean;
          default "true";
          description "Used to enable or disable a congestion-handling-policy.
          When disabled, the following alarm is raised:
          ADP Diameter Managed Object Disabled
          Update Effect: When enabled, the Diameter Service will apply
          the congestion-handling-policy configuration for scoped Diameter
          Peers.
          When disabled, the Diameter Service will apply the default
          behavior for Diameter Peer connection congestion handling.";
        }
        leaf congestion-threshold-raise-level {
          type uint16 {
            range "0..100";
          }
          default "85";
          description "Used to specify the arm threshold the congestion
          handling policy is to be applied over the congested diameter peer
          connections of scoped Diameter Peers. The congested peer
          connection will be temporarily removed from the possible routes
          determined based on loaded routing table.
          The value, in percentage representation, represents the
          utilization level of the internal queue of the Local Endpoint used
          to send egress messages towards the scoped Diameter Peer.
          Update Effect: When set, the Diameter Service will apply the
          new threshold value.";
        }
        leaf congestion-threshold-cease-level {
          type uint16 {
            range "0..100";
          }
          default "75";
          description "Used to specify the disarm threshold the congestion
          handling policy is to be ceased over the Diameter Peer connections,
          of scoped Diameter Peers, getting out of congestion. The
          Peer connection will be considered again as possible route to
          be used based on loaded routing table.
          The value, in percentage representation, represents the
          utilization level of the internal queue of the Local Endpoint used
          to send egress messages towards the scoped Diameter Peer.
          Update Effect: When set, the Diameter Service will apply the
          new threshold value.";
        }
        leaf user-label {
          type string;
          description "Label for free use.";
        }
      }
    }
    /*********************************************************************/
    container load-control {
      description "Container holding overload protection and load regulation
       parameters effective on stack level.";
      //overload-protection
      leaf ingress-connection-backlog-limit {
        type uint32;
        default "0";
        description "Used to limit the number of parallel incoming transport
        connections per computing resource (Diameter POD) being setup to the
        stack at the same time. Parallel TCP and SCTP connections are counted
        until capability exchange is finished, that is when CEA is sent.
        This is an overload protection function to improve robustness against
        extreme load peaks. It ensures that Diameter remains in service even at
        significant increase of incoming transport connections.
        Rejected attempts are measured by related
        Diameter_ConnTermDrop_OverloadProtection counter.
        By default(value 0), backlog of incoming connections is not limited.
        Calculated value shall be the result of careful user application
        dimensioning including load tests on different Diameter cluster sizes
        with various number of client Peer connections built at the same time.
        Update Effect: Diameter Service applies the configured backlog limit.";
      }
      leaf user-label {
        type string;
        description "Label for free use.";
      }
      /*********************************************************************/
      container load-regulation {
        must '( not(enabled) ) or ( enabled = "false" ) or '
        + '( count(current()/regulator[enabled = "true"] ) != 0 )' {
          error-message "enabled load-regulation must have at least one enabled
          regulator";
          error-app-tag "load-regulation-regulator";
        }
        status current {
          yexte:preliminary;
          yexte:status-information "Under development. Diameter stack load
          regulation function has not been verified by user applications, yet.";
        }
        description "Container holding stack level load regulation related
        functions. Load regulation function secures high diameter traffic
        throughput at sustained high load via rejecting excessive ingress
        requests with with DIAMETER_TOO_BUSY result code. The aim of the load
        regulation mechanism is to regulate the incoming traffic level in a way
        that it maximizes the amount of successfully handled traffic on a
        compute resource at sustained overload, that is, to keep the load on
        regulation-limit level or below.
        Load regulation algorithm of Diameter can be applied over several
        measurement types monitored on stack level, see measurement-name of
        regulator. Measurement value samples are fetched at every
        granularity-period for each measurement. The number of
        granularity-period samplings used to calculate trends can be configured
        both for short and long term trend prediction.
        If the utilization level of any of the monitored measurement types goes
        above the configured hysteresis-on-limit resource utilization level, the
        load regulation mechanism is turned on, if it goes below the configured
        hysteresis-off-limit resource utilization level, the load regulation
        mechanism is turned off. The hysteresis-on-limit and
        hysteresis-off-limit utilization limits are set relative but lower or
        equal to the regulation-limit parameter that configures the engineered
        capacity of the resources for a certain system type configuration.
        Load regulation is not able to tolerate the negative feedback caused by
        the retry mechanism of the Peer node, hence make sure that retry
        function is turned off in the Peer. (In Diameter GS configuration see
        /diameter/service/request-send-max-retry). To lessen the load caused by
        Peer retries, incoming resent requests (with T-flag set) are dropped
        when regulation is taking place (when requests are rejected by load
        regulation).
        To save resources, the higher the rejection rate the less incoming
        requests are answered with DIAMETER_TOO_BUSY, the rest of the incoming
        requests are simply dropped.";
        leaf enabled {
          type boolean;
          default "false";
          description "Used to enable or disable load regulation in Diameter.
          Update Effect: When enabled, the Diameter Service regulates ingress
          traffic by the configured regulators. In this case, configured
          `requests` must be equal to configured `limit` value in Diameter helm
          resources configuration.
          When disabled (by default), no load regulation is applied.";
        }
        leaf granularity-period {
          type uint32 {
            range "1000..300000";
          }
          units "milliseconds";
          default "1000";
          description "Granularity period of load regulation. It defines how
          often the measurement values are updated for load regulation
          calculation.
          Update Effect: Diameter Service applies load regulation with the
          defined granularity.";
        }
        leaf reject-rate-aging-step {
          type uint16 {
            range "0..100";
          }
          units "Percentage";
          default "10";
          description "Used to set the size of the step in percentage used
          during aging. Aging of reject rate is applied when no measurement
          value has been received during the granularity period. In this case,
          the new reject rate value is calculated via decreasing the last value
          with reject-rate-aging-step percentage.
          Reject rate defines the percentage of the traffic that is to be
          rejected when load regulation is applied.
          Aging prevents freeze of load regulation when no measurement values
          are received.
          Update Effect: Diameter Service applies load regulation with the
          defined aging step.";
        }
        leaf history-size {
          type uint16 {
            range "10..500";
          }
          units "Number of samples";
          default "256";
          description "Used to set size of the stored history.
          Update Effect: Load regulation history is maintained and dumped with
          defined size.";
        }
        leaf user-label {
          type string;
          description "Label for free use.";
        }
        action dump-history {
          description "Used to dump textual representation of the load
          regulation history for troubleshooting purposes. Dumps configured size
          of history for each Diameter POD marked with its POD_IP.
          For example:
          LRHistory from Diameter POD 192.168.98.26
          calls: I/A/R: 10/5/5 [ 3:5/0/5 12:5/5/0 ] -REJ-, where
          I/A/R: Number of Incoming/Accepted/Rejected requests. First the
          accumulated values then in squared brackets values per priority, with
          lowest priority first (in increasing priority order).
          -REJ- : Optionally highlights the existence of rejection event in the
          granularity.
          prio/RR: 3/cccc0000, where
          prio = priority of rejection. Requests with lower priority have been
          rejected with DIAMETER_TOO_BUSY or dropped, higher priority requests
          have been kept.
          RR = rejection rate compared to FFFFFFFF
          For example:
          datastr: [CG:Diameter.CG.CPULoad.Total][SN=eric-stm-diameter-xx,
          CG=diameter](OK) MVAL:25.100005 MAX:1000 LIM:900 ON:700 OFF:600 
          VAL:251 ST:190 LT:108 RR:00000000(-674289615) RRR:00000000
          datastr: [CG:Diameter.CG.Mem.Used.ToRequest.perc][SN=eric-stm-diaXXX,
          CG=diameter](OK) MVAL:84.015137 MAX:1000 LIM:800 ON:600 OFF:500 
          VAL:840 ST:840 LT:811 RR:6b81947e(73005990) RRR:6b81947e
          Abbreviations used in datastr lines besides measurement type:
          SN    : Source of measurement
          CG    : Container/POD identifier
          (OK)  : Status of measurement [OK|NoVal|OldVal], where 
          NoVal : no value received
          OldVal: Old value from previous granularity
          MVAL  : Measured value
          MAX   : Configured maximum-value multiplied by 10
          LIM   : Configured regulation-limit multiplied by 10
          ON    : Configured hysteresis-on-limit multiplied by 10
          OFF   : Configured hysteresis-off-limit multiplied by 10
          VAL   : Measured value multiplied by 10
          ST    : Calculated short term average
          LT    : Calculated long term average
          RR    : Reject Rate compared to FFFFFFFF, in brackets its delta
          RRR   : used reject rate, where RRR <= RR or RRR = 0, when VAL < OFF";
          output {
            uses action-result;
          }
        }
        list regulator {
          must '( enabled = "false" ) or '
          + '( hysteresis-on-limit <= regulation-limit )' {
            error-message "An enabled regulator must have lower or equal
            hysteresis-on-limit than regulation-limit";
            error-app-tag "regulator-hysteresis-on-limit-regulation-limit";
          }
          must '( enabled = "false" ) or '
          + '( hysteresis-off-limit <= hysteresis-on-limit )' {
            error-message "An enabled regulator must have lower or equal
            hysteresis-off-limit than hysteresis-on-limit";
            error-app-tag "regulator-hysteresis-off-limit-hysteresis-on-limit";
          }
          must '( enabled = "false" ) or '
          + '( short-term-samples <= long-term-samples )' {
            error-message "An enabled regulator must have lower or equal
            short-term-samples than long-term-samples";
            error-app-tag "regulator-short-term-samples-long-term-samples";
          }
          key "id";
          description "Specifies a regulator function of Diameter load
          regulation.";
          leaf id {
            type string;
            description "Key of the regulator.";
          }
          leaf enabled {
            type boolean;
            default "true";
            description "Can be used to enable or disable the regulator.
            Update Effect: When enabled, Diameter Service will apply
            regulation defined hereby.";
          }
          leaf measurement-name {
            type enumeration {
              enum cpuload {
                value 0;
                description "Total CPU load of Diameter container as percentage
                of related K8S resource limit.";
              }
              enum memory-utilization {
                value 1;
                description "Diameter container memory usage as percentage of
                related K8S resource request.";
              }
//               enum latency {
//                 value 2;
//                 description "Diameter cluster local traffic latency
//                 (DiaServerPOD--[gRPCPOD]--UserApplicationPOD there and
//                 back).";
//               }
            }
            default cpuload;
            description "Defines the measurement type used by the regulator.
            Update Effect: Diameter Service applies load regulation using the
            defined measurement.";
          }
          leaf maximum-value {
            type uint32;
            units "Measurement value";
            default "100";
            description "Used to specify the upper limit for the releated
            measurement type to give a base for the related percentage based
            parameters defined for the regulator.
            Percentage based measurement types should keep default 100.
            Shall be used for measurement types that are not percentage
            based, like for example latency.
            Update Effect: When set, the Diameter Service starts regulation
            according to the specified value.";
          }
          leaf regulation-limit {
            type uint16 {
              range "0..100";
            }
            units "Percentage";
            default "80";
            description "Used to specify the limit of the regulation in
            percentage relative to the maximum-value of the configured
            measurement. If resource usage rises above the specified load
            regulation limit, reject rate of ingress requests is significantly
            increased.
            Load regulation aims to keep the resource consumption around/under
            the configured regulation limit.
            The stack increases the reject rate (RR) until the configured
            regulation limit (LIM) is reached/crossed by the measured value
            (MVAL/VAL). Until the reject rate is not zero the stack answers
            messages with DIAMETER_TOO_BUSY (or just drops them) to decrease the
            resource consumption.
            Ingress requests rejected by load regulation are measured by
            Diameter_IngressReqMsgDiscarded_DiaServerLoadReg meas type. Diameter
            user applications can configure PM threshold based alarm on it.
            Update Effect: When set, the Diameter Service starts regulation
            according to the specified value.";
          }
          leaf hysteresis-on-limit {
            type uint16 {
              range "0..100";
            }
            units "Percentage";
            default "60";
            description "Used to set the utilization level the load regulation
            mechanism is to be switched on. It is to be expressed as a
            percentage value relative to the configured maximum-value
            and lower or equal to regulation-limit.
            Update Effect: When set, the Diameter Service starts regulation
            according to the specified value.";
          }
          leaf hysteresis-off-limit {
            type uint16 {
              range "0..100";
            }
            units "Percentage";
            default "50";
            description "Used to set the utilization level the load regulation
            mechanism is to be switched off. It is to be expressed as a
            percentage value relative to the configured maximum-value and
            lower or equal to regulation-limit and hysteresis-on-limit.
            Update Effect: When set, the Diameter Service starts regulation
            according to the specified value.";
          }
          leaf short-term-samples {
            type uint16 {
              range "1..300";
            }
            units "Number of samples";
            default "1";
            description "Used to set the short-term monitoring interval (number
            of measurement samples) for resource utilization trend prediction.
            It expresses how many load-regulation granularity-period to consider
            for short term sampling.
            Update Effect: When set, the Diameter Service starts regulation
            according to the specified value.";
          }
          leaf long-term-samples {
            type uint16 {
              range "1..300";
            }
            units "Number of samples";
            default "5";
            description "Used to set the long-term monitoring interval (number
            of measurement samples) for resource utilization trend prediction.
            It expresses how many load-regulation granularity-period to consider
            for long term sampling.
            Update Effect: When set, the Diameter Service starts regulation
            according to the specified value.";
          }
          leaf user-label {
            type string;
            description "Label for free use.";
          }
        }
      }
    }
  }

  /*************** Common types for action handling ********************/

  typedef connection-initiation-type {
    type enumeration {
      enum local-endpoint {
        value 0;
        description "The local endpoint is the initiator, that is the local
        node is acting as client.";
      }
      enum remote-endpoint {
        value 1;
        description "The remote endpoint is the initiator, that is the local
        node is acting as server.";
      }
    }
    description "Connection can be initiated by the own Node or by the Peer.";
  }

  typedef transport-type {
    type enumeration {
      enum tcp {
        value 0;
        description "TCP protocol in action outputs";
      }
      enum sctp {
        value 1;
        description "SCTP protocol in action outputs";
      }
    }
    description "Transport type in action outputs";
  }

  grouping peer-properties {
    leaf type {
      type enumeration {
        enum all {
          value 0;
          description "Both static and dynamic.";
        }
        enum static {
          value 1;
          description "The relevant Peer is configured in a static way, see
            static-peer.";
        }
        enum dynamic {
          value 2;
          description "Used for dynamic Peers. That is, when the relevant
          Peer appears as result of its matching to the conditions expressed
          through related dynamic-peer-acceptor.";
        }
      }
      description "Used to scope on the local representation of the Diameter
      Peer.";
    }
    leaf state {
      type enumeration {
        enum all {
          value 0;
          description "Both available and unavailable.";
        }
        enum available {
          value 1;
          description "The relevant Peer is available. That is, there is at
          least a Peer connection setup towards it and used by AAA service.";
        }
        enum unavailable {
          value 2;
          description "The relevant Peer is unavailable. That is, there is
          no any active Diameter Peer connection established towards related
          Peer. This presence state is only used in the context of static Peers.
          Not applicable for dynamic Peers.";
        }
      }
      description "Used to scope on the availability of the Diameter Peer
      (presence state).";
    }
    description "Peer properties of action output.";
  }

  grouping action-result {
    description "Common output for diameter actions.";
    leaf success {
      type boolean;
      mandatory true;
      description "Diameter action returns true in case of success, false
      in case of any failure.";
    }
    leaf result {
      type string;
      description "Optional result string of the diameter action. Can hold
      error string in case of failures.";
    }
  }

  grouping peer-list-information {
    description "Common output for diameter actions returning list of Diameter
    Peers.";
    uses action-result;
    container structured-result {
      presence "Optional output";//needed for generated json maybevalue
      description "Optional JSON output returned by the diameter action.";
      list peer-list {
        key "origin-host";
        description "List of pers in action outputs";
        leaf origin-host {
          type string;
          description "Origin-Host of the Diameter Peer.";
        }
        uses peer-properties;
      }
    }
  }

  grouping peer-capabilities {
    description "Peer result.";
    leaf origin-host {
      type string;
      mandatory true;
      description "Origin-Host of the Diameter Peer.";
    }
    leaf origin-realm {
      type string;
      description "Origin Realm of the Diameter Peer.";
    }
    leaf product-name {
      type string;
      description "The name of the product behind the Diameter Peer.";
    }
    leaf vendor-id {
      type uint32;
      description "The identity of the vendor implementing the Peer product
      specified for product-name";
    }
    leaf firmware-revision {
      type uint32;
      description "The revision of the software product specified for
      product-name.";
    }
  }

  grouping peer-information {
    description "Common output for diameter actions returning a Diameter Peer.";
    uses action-result;
    container structured-result {
      presence "Optional output";//needed for generated json maybevalue
      description "Optional JSON output returned by the diameter action.";
      uses peer-capabilities;
      uses peer-properties;
      leaf connection-nr {
        type uint32;
        description "The actual number of connections built to/from this
        Diameter Peer.";
      }
      leaf-list accepted-by {
        type string;
        description "Identifier of the dynamic-peer-acceptor of this
        connection.";
      }
    }
  }

  grouping connection-list-information {
    description "Common output for diameter actions returning list of
    connections.";
    uses action-result;
    container structured-result {
      presence "Optional output";//needed for generated json maybevalue
      description "Optional JSON output returned by the diameter action.";
      leaf origin-host {
        type string;
        mandatory true;
        description "Origin-Host of the connected Diameter Peer.";
      }
      leaf connection-nr {
        type uint32;
        mandatory true;
        description "The number of connections built to/from this Diameter
        Peer.";
      }
      list connections {
        key "connection-id";
        description "List of the Diameter Peer connections per Diameter Peer.";
        leaf connection-id {
          type string;
          mandatory true;
          description "The unique identifier of the connection in diameter.";
        }
        leaf connection-initiation {
          type connection-initiation-type;
          mandatory true;
          description "Connection can be initiated by the own Node or by
          the Peer.";
        }
        leaf transport-type {
          type transport-type;
          mandatory true;
          description "Transport type in action outputs";
        }
        leaf uptime {
          type uint32;
          mandatory true;
          description "Uptime of connection in seconds.";
        }
        leaf acceptor-nr {
          type uint32;
          mandatory true;
          description "Number of dynamic acceptors for server connections.";
        }
      }
    }
  }

  grouping connection-data {
    leaf connection-id {
      type string;
      mandatory true;
      description "The unique identifier of the connection in diameter.";
    }
    leaf transport-type {
      type transport-type;
      mandatory true;
      description "Diameter supports TCP and SCTP transport.";
    }
    leaf uptime {
      type uint32;
      mandatory true;
      description "Uptime of connection in seconds.";
    }
    description "Common data of connections";
  }

  grouping connection-information {
    description "Common output for diameter actions returning a connection.";
    uses action-result;
    container structured-result {
      presence "Optional output";//needed for generated json maybevalue
      description "Optional JSON output returned by the diameter action.";
      uses connection-data;
      leaf connection-initiation {
        type connection-initiation-type;
        mandatory true;
        description "Connection can be initiated by the own Node or by
        the Peer.";
      }
      container local-endpoint-data {
        description "Information of local endpoint in action outputs";
        leaf local-endpoint-id {
          type string;
          mandatory true;
          description "The key of the local-endpoint.";
        }
        leaf-list local-addresses {
          type string;
          description "Address of local endpoint.";
        }
        leaf origin-host {
          type string;
          mandatory true;
          description "Origin-Host of the own Diameter Node.";
        }
        leaf origin-realm {
          type string;
          mandatory true;
          description "Origin-Realm of the own Diameter Node.";
        }
      }
      container remote-endpoint-data {
        description "Information of remote endpoint in action outputs";
        leaf-list remote-addresses {
          type string;
          description "Address of remote endpoint.";
        }
        leaf origin-host {
          type string;
          mandatory true;
          description "Origin-Host of the Diameter Peer.";
        }
        leaf origin-realm {
          type string;
          mandatory true;
          description "Origin-Realm of the Diameter Peer.";
        }
        leaf-list accepted-by {
          type string;
          description "Identifier of the dynamic-peer-acceptor of this
          connection.";
        }
      }
    }
  }

  grouping transport-information {
    description "Output for diameter action dump-transport.";
    uses action-result;
    container structured-result {
      presence "Optional output";//needed for generated json maybevalue
      description "Optional JSON output returned by the diameter action.";
      list own-nodes {
        key "origin-host";
        description "Information about own Diameter Node.";
        list listeners {
          key "local-endpoint-id";
          description "Transport listeners of the own Node";
          leaf local-endpoint-id {
            type string;
            description "Internal key of local endpoint.";
          }
          leaf-list listener-Ids {
            type string;
            description "identifier of the transport listener endpoints.";
          }
          leaf-list local-addresses {
            type string;
            description "Addresses of local endpoint.";
          }
          leaf transport-type {
            type transport-type;
            description "Diameter supports TCP and SCTP transport.";
          }
        }
        leaf origin-host {
          type string;
          description "Origin-Host of the own Diameter Node.";
        }
        leaf origin-realm {
          type string;
          description "Origin-Realm of the own Diameter Node.";
        }
        list peers {
          key "origin-host";
          description "Common data of Peers";
          uses peer-capabilities;
          list connections {
            key "local-endpoint-id";
            description "Peer connections.";
            leaf local-endpoint-id {
              type string;
              description "Internal key of local endpoint.";
            }
            leaf-list accepted-by {
              type string;
              description "Identifier of the dynamic-peer-acceptor of this
              connection.";
            }
            uses connection-data;
            leaf-list local-addresses {
              type string;
              description "Address of local endpoint.";
            }
            leaf-list remote-addresses {
              type string;
              description "Address of remote endpoint.";
            }
          }
        }
      }
    }
  }
  /*************** Common types ********************/
  // Until ietf-tls-common is not deployed by YP or available in EYang
  // define local copies that will be deprecated later
  typedef tls-1_2-local-cipher-list-enum {
            //preferred: L4 + no CBC (only GCM)
            //AES or Chacha20 , SHA2, SHA3 family, RSA (3k), ECDHE
            type enumeration {
              enum ecdhe-rsa-with-aes-128-gcm-sha256 {
                value 0;
                description "Cipher suite
                TLS_ECDHE_RSA_WITH_AES_128_GCM_SHA256.";
                reference "RFC 5289: TLS Elliptic Curve Cipher Suites with
                 SHA-256/384 and AES Galois Counter Mode (GCM)";
              }
              enum ecdhe-rsa-with-aes-256-gcm-sha384 {
                value 1;
                description "Cipher suite
                TLS_ECDHE_RSA_WITH_AES_256_GCM_SHA384.";
                reference "RFC 5289: TLS Elliptic Curve Cipher Suites with
                 SHA-256/384 and AES Galois Counter Mode (GCM)";
              }
              enum ecdhe-ecdsa-with-aes-128-gcm-sha256 {
                value 2;
                description "Cipher suite
                  TLS_ECDHE_ECDSA_WITH_AES_128_GCM_SHA256.";
                reference "RFC 5289: TLS Elliptic Curve Cipher Suites with
                 SHA-256/384 and AES Galois Counter Mode (GCM)";
              }
              enum ecdhe-ecdsa-with-aes-256-gcm-sha384 {
                value 3;
                description "Cipher suite
                  TLS_ECDHE_ECDSA_WITH_AES_256_GCM_SHA384.";
                reference "RFC 5289: TLS Elliptic Curve Cipher Suites with
                 SHA-256/384 and AES Galois Counter Mode (GCM)";
              }
              //some CHACHA20_POLY1305 as a safe alternative besides AES
              //with some performance penalty
              //ecdhe-rsa-chacha20-poly1305
              enum ecdhe-rsa-with-chacha20-poly1305-sha256 {
                value 4;
                description "Cipher suite
                  TLS_ECDHE_RSA_WITH_CHACHA20_POLY1305_SHA256.";
                reference "RFC 7905: ChaCha20-Poly1305 Cipher Suites for
                Transport Layer Security (TLS)";
              }
              //ecdhe-ecdsa-chacha20-poly1305
              enum ecdhe-ecdsa-with-chacha20-poly1305-sha256 {
                value 5;
                description "Cipher suite
                  TLS_ECDHE_ECDSA_WITH_CHACHA20_POLY1305_SHA256.";
                reference "RFC 7905: ChaCha20-Poly1305 Cipher Suites for
                Transport Layer Security (TLS)";
              }
              //some weaker ciphers for the sake of compatibility
              //AES-x-CBC from ietf-tls-common with alarm
              enum rsa-with-aes-128-cbc-sha {
                value 6;
                description "Cipher suite
                  TLS_RSA_WITH_AES_128_CBC_SHA."; //BL_RFC7540
                reference "RFC 5246: The Transport Layer Security (TLS) Protocol
                  Version 1.2, https://tools.ietf.org/html/rfc7540#appendix-A";
              }
              enum rsa-with-aes-256-cbc-sha {
                value 7;
                description "Cipher suite
                  TLS_RSA_WITH_AES_256_CBC_SHA."; //BL_RFC7540
                reference "RFC 5246: The Transport Layer Security (TLS) Protocol
                  Version 1.2, https://tools.ietf.org/html/rfc7540#appendix-A";
              }
              enum rsa-with-aes-128-cbc-sha256 {
                value 8;
                description "Cipher suite
                  TLS_RSA_WITH_AES_128_CBC_SHA256."; //BL_RFC7540
                reference "RFC 5246: The Transport Layer Security (TLS) Protocol
                  Version 1.2, https://tools.ietf.org/html/rfc7540#appendix-A";
              }
              enum rsa-with-aes-256-cbc-sha256 {
                value 9;
                description "Cipher suite
                  TLS_RSA_WITH_AES_256_CBC_SHA256."; //BL_RFC7540
                reference "RFC 5246: The Transport Layer Security (TLS) Protocol
                  Version 1.2, https://tools.ietf.org/html/rfc7540#appendix-A";
              }
              enum dhe-rsa-with-aes-128-cbc-sha {
                value 10;
                description "Cipher suite
                  TLS_DHE_RSA_WITH_AES_128_CBC_SHA."; //BL_RFC7540
                reference "RFC 5246: The Transport Layer Security (TLS) Protocol
                  Version 1.2, https://tools.ietf.org/html/rfc7540#appendix-A";
              }
              enum dhe-rsa-with-aes-256-cbc-sha {
                value 11;
                description "Cipher suite
                  TLS_DHE_RSA_WITH_AES_256_CBC_SHA."; //BL_RFC7540
                reference "RFC 5246: The Transport Layer Security (TLS) Protocol
                  Version 1.2, https://tools.ietf.org/html/rfc7540#appendix-A";
              }
              enum dhe-rsa-with-aes-128-cbc-sha256 {
                value 12;
                description "Cipher suite
                  TLS_DHE_RSA_WITH_AES_128_CBC_SHA256."; //BL_RFC7540
                reference "RFC 5246: The Transport Layer Security (TLS) Protocol
                  Version 1.2, https://tools.ietf.org/html/rfc7540#appendix-A";
              }
              enum dhe-rsa-with-aes-256-cbc-sha256 {
                value 13;
                description "Cipher suite
                  TLS_DHE_RSA_WITH_AES_256_CBC_SHA256."; //BL_RFC7540
                reference "RFC 5246: The Transport Layer Security (TLS) Protocol
                  Version 1.2, https://tools.ietf.org/html/rfc7540#appendix-A";
              }
              enum ecdhe-ecdsa-with-aes-128-cbc-sha256 {
                value 14;
                description "Cipher suite
                  TLS_ECDHE_ECDSA_WITH_AES_128_CBC_SHA256."; //BL_RFC7540
                reference "RFC 5289: TLS Elliptic Curve Cipher Suites with
                 SHA-256/384 and AES Galois Counter Mode (GCM),
                 https://tools.ietf.org/html/rfc7540#appendix-A";
              }
              enum ecdhe-ecdsa-with-aes-256-cbc-sha384 {
                value 15;
                description "Cipher suite
                  TLS_ECDHE_ECDSA_WITH_AES_256_CBC_SHA384."; //BL_RFC7540
                reference "RFC 5289: TLS Elliptic Curve Cipher Suites with
                 SHA-256/384 and AES Galois Counter Mode (GCM),
                 https://tools.ietf.org/html/rfc7540#appendix-A";
              }
              enum ecdhe-rsa-with-aes-128-cbc-sha256 {
                value 16;
                description "Cipher suite
                  TLS_ECDHE_RSA_WITH_AES_128_CBC_SHA256."; //BL_RFC7540
                reference "RFC 5289: TLS Elliptic Curve Cipher Suites with
                 SHA-256/384 and AES Galois Counter Mode (GCM),
                 https://tools.ietf.org/html/rfc7540#appendix-A";
              }
              enum ecdhe-rsa-with-aes-256-cbc-sha384 {
                value 17;
                description "Cipher suite
                  TLS_ECDHE_RSA_WITH_AES_256_CBC_SHA384."; //BL_RFC7540
                reference "RFC 5289: TLS Elliptic Curve Cipher Suites with
                 SHA-256/384 and AES Galois Counter Mode (GCM),
                 https://tools.ietf.org/html/rfc7540#appendix-A";
              }
              enum ecdhe-rsa-with-aes-128-cbc-sha {
                value 18;
                description "Cipher suite
                  TLS_ECDHE_RSA_WITH_AES_128_CBC_SHA."; //BL_RFC7540
                reference "RFC 8422: Elliptic Curve Cryptography (ECC) Cipher
                  Suites for Transport Layer Security (TLS),
                  https://tools.ietf.org/html/rfc7540#appendix-A";
              }
              enum ecdhe-rsa-with-aes-256-cbc-sha {
                value 19;
                description "Cipher suite
                  TLS_ECDHE_RSA_WITH_AES_256_CBC_SHA."; //BL_RFC7540
                reference "RFC 8422: Elliptic Curve Cryptography (ECC) Cipher
                  Suites for Transport Layer Security (TLS),
                  https://tools.ietf.org/html/rfc7540#appendix-A";
              }
              //3DES-EDE-CBC from ietf-tls-common with alarm
              enum rsa-with-3des-ede-cbc-sha {
                value 20;
                description "Cipher suite
                  TLS_RSA_WITH_3DES_EDE_CBC_SHA."; //BL_RFC7540
                reference "RFC 5246: The Transport Layer Security (TLS) Protocol
                  Version 1.2, https://tools.ietf.org/html/rfc7540#appendix-A";
              }
              enum ecdhe-rsa-with-3des-ede-cbc-sha {
                value 21;
                description "Cipher suite
                  TLS_ECDHE_RSA_WITH_3DES_EDE_CBC_SHA."; //BL_RFC7540
                reference "RFC 8422: Elliptic Curve Cryptography (ECC) Cipher
                  Suites for Transport Layer Security (TLS),
                  https://tools.ietf.org/html/rfc7540#appendix-A";
              }
            }
    description "NA";
  }
}
